FME workspace Ejercicio3_Inicio.fmw

Parameters:
- SourceDataset_FILEGDB = $(FME_MF_DIR)Data\CallejeroMadrid.gdb   # Geodatabase de Archivos
- SourceDataset_CSV2_3 = $(FME_MF_DIR)Data\mercadosmunicipales.csv   # Archivos CSV (Comma Separated Value) de Origen
- SourceDataset_XLSXR = $(FME_MF_DIR)Data\CortesTrafico.xlsx   # Archivos Microsoft Excel de Origen
- DestDataset_XLSXW = C:\FMEData\Output\Informe_CallesCortadas.xlsx   # Archivo Microsoft Excel de Destino

Readers:
- FILEGDB_2: FILEGDB from $(SourceDataset_FILEGDB)
- CSV2_1: CSV2 from $(SourceDataset_CSV2_3)
- XLSXR_2: XLSXR from $(SourceDataset_XLSXR)

Writers:
- XLSXW_2: XLSXW to $(DestDataset_XLSXW)

CallejeroMadrid (reader FILEGDB_2)
    attributes: CDMUNI text(254), VIA_NOM text(200), CDTVIA text(254), DSPART text(254), DSVIAL text(254), GEOMETRY double, OBJECTID objectid
    -> FeatureJoiner [LEFT]
CSV (reader CSV2_1)
    attributes: PK uint32, NOMBRE varchar(47), DESCRIPCION-ENTIDAD varchar(1577), HORARIO varchar(399), EQUIPAMIENTO varchar(65), NOMBRE-VIA varchar(24), NUM uint32, DISTRITO varchar(18), COORDENADA-X x_coordinate, COORDENADA-Y y_coordinate, LATITUD varchar(22), LONGITUD varchar(23)
    -> CoordinateSystemSetter
CoordinateSystemSetter
    COORDSYS = ETRS89.UTM-30N
    -> NeighborFinder [BASE]
Cortes (reader XLSXR_2)
    attributes: Calle Cortada char(35)
    -> FeatureJoiner [RIGHT]
FeatureJoiner
    ATTR_CONFLICT_RES_LOOKUP = USE_LEFT
    GEOMETRY_HANDLING_LOOKUP = USE_LEFT
    JOIN_KEYS = VIA_NOM Calle Cortada AUTO
    JOIN_MODE = Inner
    ATTR_CONFLICT_RES = Prefer Left
    GEOMETRY_HANDLING = Prefer Left
    JOINED -> NeighborFinder [CANDIDATE]
NeighborFinder
    CANDIDATES_FIRST = No
    INSERT_VERTEX = No
    K = 1
    MAX = 50
    MEASURES_FROM_CANDIDATE = Yes
    MEASURE_TYPE = Continuous
    MODE = Bases and Candidates
    TREAT_POLYGON_AS = Lines
Informe (writer XLSXW_2)
