FME workspace Ejercicio2_Inicio.fmw

Parameters:
- SourceDataset_FILEGDB = $(FME_MF_DIR)Data\CallejeroMadrid.gdb   # Geodatabase de Archivos
- SourceDataset_CSV2_3 = $(FME_MF_DIR)Data\mercadosmunicipales.csv   # Archivos CSV (Comma Separated Value) de Origen
- SourceDataset_XLSXR = $(FME_MF_DIR)Data\CortesTrafico.xlsx   # Archivos Microsoft Excel de Origen
- DestDataset_XLSXW = C:\FMEData\Output\Informe_CallesCortadas.xlsx   # Archivo Microsoft Excel de Destino

Readers:
- FILEGDB_2: FILEGDB from $(SourceDataset_FILEGDB)
- CSV2_1: CSV2 from $(SourceDataset_CSV2_3)
- XLSXR_2: XLSXR from $(SourceDataset_XLSXR)

Writers:
- XLSXW_1: XLSXW to $(DestDataset_XLSXW)

CallejeroMadrid (reader FILEGDB_2)
    attributes: CDMUNI text(254), VIA_NOM text(200), CDTVIA text(254), DSPART text(254), DSVIAL text(254), GEOMETRY double, OBJECTID objectid
CSV (reader CSV2_1)
    attributes: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
Cortes (reader XLSXR_2)
    attributes: Calle Cortada char(35)
Hoja1 (writer XLSXW_1)
