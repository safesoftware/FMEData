FME workspace LetDatabaseDoTheWork.fmw

Parameters:
- SourceDataset_ORACLE_SPATIAL = local XE as FME   # Connection
- SourceDataset_ESRISHAPE = C:\FMEData2017\Resources\DatabaseWorkshop\sourcedata\canada.shp   # Source Esri Shapefile(s)

Readers:
- ORACLE_SPATIAL_1: ORACLE_SPATIAL from $(SourceDataset_ORACLE_SPATIAL)
- ORACLE_SPATIAL_2: ORACLE_SPATIAL from $(SourceDataset_ORACLE_SPATIAL)
- ORACLE_SPATIAL_3: ORACLE_SPATIAL from $(SourceDataset_ORACLE_SPATIAL)
- ORACLE_SPATIAL_4: ORACLE_SPATIAL from $(SourceDataset_ORACLE_SPATIAL)
- ORACLE_SPATIAL_5: ORACLE_SPATIAL from $(SourceDataset_ORACLE_SPATIAL)
- ORACLE_SPATIAL_6: ORACLE_SPATIAL from $(SourceDataset_ORACLE_SPATIAL)
- ESRISHAPE_1: ESRISHAPE from $(SourceDataset_ESRISHAPE)
- ORACLE_SPATIAL_7: ORACLE_SPATIAL from $(SourceDataset_ORACLE_SPATIAL) in LL84

COUNTRIES (reader ORACLE_SPATIAL_5)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> AttributeFilter [off]
    -> Tester [off]
AttributeFilter [off]
    ATTR_NAME = FEATURECLASS
    ATTR_VALUES = <Empty>,P,<Missing>,<Null>,<Unfiltered>
    P -> ToFilter [off]
ToFilter: Inspector [off]
Tester [off]
    TEST_CLAUSE = TEST @Value(FEATURECLASS) = P
    BOOL_OP = OR
    TEST_DESCRIPTION = ""
    TEST_MODE = Automatic
    PASSED -> ToTest [off]
ToTest: Inspector [off]

Bookmark: Ex0. Read everything and filter with TestFilter
  This is what you  want to avoid if you can. Reading all the data fomr your table and then have FME fiter the data you need.
Note: Over 2 Million Features
COUNTRIES (reader ORACLE_SPATIAL_1)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> TestFilter [off]
TestFilter [off]
    TEST_LIST:
      BOOL_OP,AND,COMPOSITE_TEST,<Unused>,TEST_CLAUSE,"TEST @Value(COUNTRYCODE) = CA
      TEST @Value(FEATURECLASS) = P",CA
    DEFAULT_VALUE = <UNFILTERED>
    CA -> COUNTRIES_3 [off]
COUNTRIES_3: Logger [off]
    MESSAGE = Feature is:
    MAXCOORDS = 20
    MAXFEATS = 20

Bookmark: Ex2. Table with Select Statement and Where Clause - CountryCode CA FeatureClass P
  Select Statment Modified - 
  NOTE When you origianlly added the Reader FME will import all attributes by default.  You must uncheck the User Attributes or the Reader will create null fields and add them to the features.  The select statement needs to include 'GEOMETRY' column if you want
  to see spatial data.
Note: Where CountryCode ='CA' / Reading 18s for / 313,270 Records
Note: Where CountryCode=CA and FeatureClass=P / Reading 19,412 Records in 5.0s
COUNTRIES (reader ORACLE_SPATIAL_3)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> COUNTRIES_2 [off]
COUNTRIES_2: Inspector [off]

Bookmark: Ex5. SQLCreator and SQLExecutor - Non-Spatial
Note: Save yourself a second... Use the SQLCreator
SQLCreator [off]
    ORACLE_SPATIAL_PERSISTENT_CONNECTION = YES
    SQL_STATEMENT = select * from countries where CountryCode='CA' and FeatureClass='P'
    EXPOSED_ATTRIBUTE_LIST = ADMIN1CODE,ADMIN2CODE,ADMIN3CODE,ADMIN4CODE,ALTERNATIVENAMES,ASCIINAME,CC2,COUNTRYCODE,DEM,ELEVATION,FEATURECLASS,FEATURECODE,GEONAMEID,LATITUDE,LONGITUDE,MODDATE,NAME,POPULATION,TIMEZONE
    ORACLE_SPATIAL_USE_UNIFIED_DATE_ATTRS = YES
    ORACLE_SPATIAL_QUERY_FEATURE_TYPES_FOR_MERGE_FILTERS = Yes
    FORMAT = ORACLE_SPATIAL
    ORACLE_SPATIAL_SERVER_TYPE = ORACLE8i
    ORACLE_SPATIAL_REMOVE_SCHEMA_QUALIFIER = NO
    ORACLE_SPATIAL_NAMED_CONNECTION = Oracle11.2 @support/support@//proserve1:1521
    ORACLE_SPATIAL_SHOW_SYSTEM_TABLES = NO
    RESULT -> SQLCreator_Result [off]
Note: SQLCreator - No Geometry 5.1s/5.2s for 19,412 Records
SQLCreator_Result: Inspector [off]
Creator [off]
    GEOMTYPE = Geometry Object
    NUM = 1
    CREATED -> SQLExecutor [INITIATOR] [off]
SQLExecutor [off]
    ORACLE_SPATIAL_PERSISTENT_CONNECTION = YES
    SQL_STATEMENT = select * from countries where CountryCode='CA' and FeatureClass='P'
    EXPOSED_ATTRIBUTE_LIST = ADMIN1CODE,ADMIN2CODE,ADMIN3CODE,ADMIN4CODE,ALTERNATIVENAMES,ASCIINAME,CC2,COUNTRYCODE,DEM,ELEVATION,FEATURECLASS,FEATURECODE,GEONAMEID,LATITUDE,LONGITUDE,MODDATE,NAME,POPULATION,TIMEZONE
    ORACLE_SPATIAL_USE_UNIFIED_DATE_ATTRS = YES
    ORACLE_SPATIAL_QUERY_FEATURE_TYPES_FOR_MERGE_FILTERS = Yes
    FORMAT = ORACLE_SPATIAL
    COMBINE_GEOM = Initiator Geometry Only
    ORACLE_SPATIAL_SERVER_TYPE = ORACLE8i
    ORACLE_SPATIAL_REMOVE_SCHEMA_QUALIFIER = NO
    ORACLE_SPATIAL_NAMED_CONNECTION = Oracle11.2 @support/support@//proserve1:1521
    COMBINE_ATTRS = Result Attributes Only
    ORACLE_SPATIAL_SHOW_SYSTEM_TABLES = NO
    RESULT -> SQLExecutor_Result [off]
Note: SQLExecutor - No Geometry 6.5s/6.6s for 19,412 Records
SQLExecutor_Result: Inspector [off]

Bookmark: Ex.7 Spatial Queries using FeatureReader
Note: canada [ESRISHAPE]
Note: Sending an area of interest to the / database so it does the spatial query and an attribute where clause / 1) Run as is and record time. / 2) Create INDEX and run again (CreateIndex). / 3) Compare times.
canada (reader ESRISHAPE_1)
    attributes: scalerank short, featurecla char(30), labelrank number(16,6), sovereignt char(254), sov_a3 char(254), adm0_dif number(16,6), level number(16,6), type char(254), admin char(254), adm0_a3 char(254), geou_dif number(16,6), geounit char(254), gu_a3 char(254), su_dif number(16,6), subunit char(254), su_a3 char(254), brk_diff number(16,6), name char(254), name_long char(254), brk_a3 char(254), brk_name char(254), brk_group char(254), abbrev char(254), postal char(254), formal_en char(254), formal_fr char(254), note_adm0 char(254), note_brk char(254), name_sort char(254), name_alt char(254),
      mapcolor7 number(16,6), mapcolor8 number(16,6), mapcolor9 number(16,6), mapcolor13 number(16,6), pop_est number(16,6), gdp_md_est number(16,6), pop_year number(16,6), lastcensus number(16,6), gdp_year number(16,6), economy char(254), income_grp char(254), wikipedia number(16,6), fips_10 char(254), iso_a2 char(254), iso_a3 char(254), iso_n3 char(254), un_a3 char(254), wb_a2 char(254), wb_a3 char(254), woe_id number(16,6), adm0_a3_is char(254), adm0_a3_us char(254), adm0_a3_un number(16,6), adm0_a3_wb number(16,6), continent char(254), region_un char(254), subregion char(254), region_wb char(254), name_len number(16,6), long_len number(16,6),
      abbrev_len number(16,6), tiny number(16,6), homepart number(16,6)
    -> FeatureReader [INITIATOR]
Note: 5.2s with Index / 5.3s without Index / Small Sample so may not show / significant difference in times.
FeatureReader
    ORACLE_SPATIAL_READ_3D_POLYGON_AS_FACE = NO
    FEATURETYPES = COUNTRIES
    ORACLE_SPATIAL_SERVER_TYPE = ORACLE8i
    ORACLE_SPATIAL_PARSE_MAPINFO_SYMBOLOGY = NO
    ORACLE_SPATIAL_USE_UNIFIED_DATE_ATTRS = YES
    ORACLE_SPATIAL_HANDLE_MULTIPLE_SPATIAL_COLUMNS = NO
    ORACLE_SPATIAL_CHUNK_SIZE = 200
    INTERACT = Intersects
    DATASET = $(SourceDataset_ORACLE_SPATIAL)
    ORACLE_SPATIAL_PERSISTENT_CONNECTION = YES
    ORACLE_SPATIAL_USE_SEARCH_ENVELOPE = NO
    OUTPUT_FEATURES_DISPLAY = Schema and Data Features
    ORACLE_SPATIAL_SHOW_SYSTEM_TABLES = NO
    ORACLE_SPATIAL_NAMED_CONNECTION = $(SourceDataset_ORACLE_SPATIAL)
    ATTRIBUTES = COUNTRIES,"GEONAMEID,NAME,ASCIINAME,ALTERNATIVENAMES,LATITUDE,LONGITUDE,FEATURECLASS,FEATURECODE,COUNTRYCODE,CC2,ADMIN1CODE,ADMIN2CODE,ADMIN3CODE,ADMIN4CODE,POPULATION,ELEVATION,DEM,TIMEZONE,MODDATE"
    WHERE = FEATURECLASS = 'P'
    ATTR_ACCUM_MODE = Only Use Result
    FORMAT = ORACLE_SPATIAL
    ORACLE_SPATIAL_QUERY_FEATURE_TYPES_FOR_MERGE_FILTERS = Yes
    ORACLE_SPATIAL_REMOVE_SCHEMA_QUALIFIER = NO
    COMBINE_GEOM = Use Result
    COUNTRIES -> FeatureReader_COUNTRIES
FeatureReader_COUNTRIES: Inspector [off]
CreateIndex: SQLCreator [off]
    ORACLE_NONSPATIAL_REMOVE_SCHEMA_QUALIFIER = NO
    SQL_STATEMENT = CREATE INDEX IDX_FEATURECLASS ON COUNTRIES (FEATURECLASS)
    ORACLE_NONSPATIAL_QUERY_FEATURE_TYPES_FOR_MERGE_FILTERS = Yes
    ORACLE_NONSPATIAL_SERVER_TYPE = ORACLE8i
    ORACLE_NONSPATIAL_USE_UNIFIED_DATE_ATTRS = YES
    ORACLE_NONSPATIAL_PERSISTENT_CONNECTION = YES
    ORACLE_NONSPATIAL_SHOW_SYSTEM_TABLES = NO
    FORMAT = ORACLE_NONSPATIAL
    DATASET = local XE as FME
    ORACLE_NONSPATIAL_NAMED_CONNECTION = local XE as FME
DropIndex: SQLCreator [off]
    ORACLE_NONSPATIAL_REMOVE_SCHEMA_QUALIFIER = NO
    SQL_STATEMENT = DROP INDEX IDX_FEATURECLASS
    ORACLE_NONSPATIAL_QUERY_FEATURE_TYPES_FOR_MERGE_FILTERS = Yes
    ORACLE_NONSPATIAL_SERVER_TYPE = ORACLE8i
    ORACLE_NONSPATIAL_USE_UNIFIED_DATE_ATTRS = YES
    ORACLE_NONSPATIAL_PERSISTENT_CONNECTION = YES
    ORACLE_NONSPATIAL_SHOW_SYSTEM_TABLES = NO
    FORMAT = ORACLE_NONSPATIAL
    DATASET = local XE as FME
    ORACLE_NONSPATIAL_NAMED_CONNECTION = local XE as FME

Bookmark: Ex.1 Table with Where Clause
  Showing  Where clause in use
  CountryCode=CA and FeatureClass=P
Note: Where COUNTRYCODE='CA' / Reading 25s / 313,270 Records
Note: Where CountryCode=CA and FeatureClass=P / Reading 19,412 Records in 6.3s
COUNTRIES (reader ORACLE_SPATIAL_2)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> COUNTRIES [off]
COUNTRIES: Inspector [off]

Bookmark: Ex3. Using a database VIEW
  View is selecting from Base Table with where clause is countrycode=CA
Note: A View on a Table / in the database with / where CountryCode ='CA' / Reading 24.9s for / 313,270 Records
Note: Where CountryCode=CA and FeatureClass=P / Reading 19,412 Records in 5.1s
V_COUNTRIES_CA (reader ORACLE_SPATIAL_4)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> V_COUNTRIES_CA
V_COUNTRIES_CA: Inspector [off]
Note: Don't forget to add / USER_SDO_GEOM_METADATA
Note: CREATE VIEW
SQLCreator_4 [off]
    ORACLE_SPATIAL_PERSISTENT_CONNECTION = YES
    SQL_STATEMENT:
      FME_SQL_DELIMITER ;

      CREATE VIEW V_COUNTRIES_CA AS SELECT * FROM COUNTRIES WHERE COUNTRYCODE = 'CA';
    ORACLE_SPATIAL_USE_UNIFIED_DATE_ATTRS = YES
    ORACLE_SPATIAL_QUERY_FEATURE_TYPES_FOR_MERGE_FILTERS = Yes
    FORMAT = ORACLE_SPATIAL
    ORACLE_SPATIAL_SERVER_TYPE = ORACLE8i
    ORACLE_SPATIAL_REMOVE_SCHEMA_QUALIFIER = NO
    DATASET = $(SourceDataset_ORACLE_SPATIAL)
    ORACLE_SPATIAL_NAMED_CONNECTION = $(SourceDataset_ORACLE_SPATIAL)
    ORACLE_SPATIAL_SHOW_SYSTEM_TABLES = NO

Bookmark: Ex.6 Table with Where Clause
  Showing  Where clause in use
  CountryCode=CA and FeatureClass=P
Note: Where CountryCode=CA and FeatureClass=P / Reading 19,412 Records with INDEX is faster than Example 1!
COUNTRIES (reader ORACLE_SPATIAL_6)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> COUNTRIES_4
COUNTRIES_4: Inspector [off]
Note: Add an Attribute Index and Demo / the difference
SQLCreator_2 [off]
    ORACLE_SPATIAL_PERSISTENT_CONNECTION = YES
    SQL_STATEMENT:
      FME_SQL_DELIMITER ;

      CREATE INDEX IDX_COUNTRIES ON COUNTRIES (COUNTRYCODE, FEATURECLASS);
    ORACLE_SPATIAL_USE_UNIFIED_DATE_ATTRS = YES
    ORACLE_SPATIAL_QUERY_FEATURE_TYPES_FOR_MERGE_FILTERS = Yes
    FORMAT = ORACLE_SPATIAL
    ORACLE_SPATIAL_SERVER_TYPE = ORACLE8i
    ORACLE_SPATIAL_REMOVE_SCHEMA_QUALIFIER = NO
    DATASET = $(SourceDataset_ORACLE_SPATIAL)
    ORACLE_SPATIAL_NAMED_CONNECTION = $(SourceDataset_ORACLE_SPATIAL)
    ORACLE_SPATIAL_SHOW_SYSTEM_TABLES = NO
Note: DROP the attribute index
SQLCreator_3 [off]
    ORACLE_SPATIAL_PERSISTENT_CONNECTION = YES
    SQL_STATEMENT:
      FME_SQL_DELIMITER ;

      DROP  INDEX IDX_COUNTRIES;
    ORACLE_SPATIAL_USE_UNIFIED_DATE_ATTRS = YES
    ORACLE_SPATIAL_QUERY_FEATURE_TYPES_FOR_MERGE_FILTERS = Yes
    FORMAT = ORACLE_SPATIAL
    ORACLE_SPATIAL_SERVER_TYPE = ORACLE8i
    ORACLE_SPATIAL_REMOVE_SCHEMA_QUALIFIER = NO
    DATASET = $(SourceDataset_ORACLE_SPATIAL)
    ORACLE_SPATIAL_NAMED_CONNECTION = $(SourceDataset_ORACLE_SPATIAL)
    ORACLE_SPATIAL_SHOW_SYSTEM_TABLES = NO

Bookmark: Ex. 8 Spatial Query using the Search Envelop
Note: Spatial Data Filter at the Database using Search / Envelope / MBR -129.2968, 48.6950 to -115.1172, 53.3866 / 36,461 Features in 8.5s Clip=Yes / 36,464 Features in 6.4s Clip=Yes / With Data Inspector Transformer disabled. / 36,464 Features in 7.9s Clip=No / 36,464 Features in 5.1s Clip=No / With Data Inspector Transformer disabled. / MBR -129.2968, 48.6950 to -120.1172, 50.3866 / 13,000 Features in 4.2s wiht Clip=Yes / 13,001 Features 3.9s wiht Clip=No / Set Your Coordinate Systems on the Reader
FME.COUNTRIES (reader ORACLE_SPATIAL_7)
    attributes: GEONAMEID number(38,0), NAME varchar2(50), ASCIINAME varchar2(50), ALTERNATIVENAMES varchar2(50), LATITUDE number, LONGITUDE number, FEATURECLASS varchar2(1), FEATURECODE varchar2(4), COUNTRYCODE varchar2(20), CC2 varchar2(20), ADMIN1CODE number(38,0), ADMIN2CODE number(38,0), ADMIN3CODE number(38,0), ADMIN4CODE number(38,0), POPULATION number(38,0), ELEVATION number, DEM number, TIMEZONE varchar2(40), MODDATE date
    -> FME.COUNTRIES
Note: For Top Peformance / Do Not Clip! / Disabled Data Inspector / (at least on Desktop)
FME.COUNTRIES: Inspector [off]

Bookmark: Ex4. Reading Data and Filtering or thinning in FME
  This demonstrates how you can improve the peformance of your workflows... by Letting the Database Do The Work
Note: To Filter or to Test... / AttributeFilter OR Tester?
Note: Takes 29.8s/33.4s/36.9s to do the same as the / above examples for 19,412 Records
Note: Takes 39.6s/41.0s/46.1s to do the same as the / above examples for 19,412 Records
Note: Filter...
