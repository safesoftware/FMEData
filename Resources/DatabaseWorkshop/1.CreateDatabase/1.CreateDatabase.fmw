FME workspace 1.CreateDatabase.fmw

Parameters:
- ORACLEDB = localhost/XE   # Service Name or Easy Connect
- SYSUSER = SYSTEM   # Enter System User
- SYSPASS =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   # Enter SYSTEM Password
- NEWUSER = FME   # Enter Your desired username

Note: Requirements: / 1) Local Oracle XE database exists / 2) Known System username and password - update related private parameters / Purpose: / This workspace creates a new user called FME in an existing local Oracle/XE / database as the SYSTEM user. Next it tests the new user by connecting to / the database. After that database directory is created, pointing to an existing folder / in c:\temp\datafiles that contains a datapump file called FMEUC.DMP. / Next we import this datapump file into the Oracle database
Creator
    GEOMTYPE = Geometry Object
    NUM = 1
    CREATED -> AttributeCreator
    CREATED -> SQLExecutor_NewUser_2 [INITIATOR]
Note: Create FME User as SYSTEM
SQLExecutor_NewUser_2
    ORACLE_NONSPATIAL_PERSISTENT_CONNECTION = YES
    ORACLE_NONSPATIAL_SERVER_TYPE = ORACLE8i
    COMBINE_ATTRS = Result Attributes Only
    ORACLE_NONSPATIAL_REMOVE_SCHEMA_QUALIFIER = NO
    SQL_STATEMENT:
      FME_SQL_DELIMITER ;
      drop user fme cascade;
      drop directory dpump_dir1;
    FORMAT = ORACLE_NONSPATIAL
    ORACLE_NONSPATIAL_SHOW_SYSTEM_TABLES = NO
    DATASET = $(ORACLEDB)
    ORACLE_NONSPATIAL_USE_UNIFIED_DATE_ATTRS = YES
    ORACLE_NONSPATIAL_PASSWORD = $(SYSPASS)
    COMBINE_GEOM = Initiator Geometry Only
    ORACLE_NONSPATIAL_USER_NAME = $(SYSUSER)
    ORACLE_NONSPATIAL_QUERY_FEATURE_TYPES_FOR_MERGE_FILTERS = Yes
    INITIATOR -> SQLExecutor_NewUser [INITIATOR]
    <REJECTED> -> SQLExecutor_NewUser [INITIATOR]
Note: Create FME User as SYSTEM
Note: SYSTEM/fmesys
SQLExecutor_NewUser
    ORACLE_NONSPATIAL_PERSISTENT_CONNECTION = YES
    ORACLE_NONSPATIAL_SERVER_TYPE = ORACLE8i
    COMBINE_ATTRS = Result Attributes Only
    ORACLE_NONSPATIAL_REMOVE_SCHEMA_QUALIFIER = NO
    SQL_STATEMENT:
      FME_SQL_DELIMITER ;
      CREATE USER $(NEWUSER) IDENTIFIED BY $(NEWUSER)
      DEFAULT TABLESPACE "USERS"
      TEMPORARY TABLESPACE "TEMP"
      ACCOUNT UNLOCK ;

      GRANT RESOURCE, CONNECT TO $(NEWUSER);

      ALTER USER $(NEWUSER) DEFAULT ROLE RESOURCE,CONNECT;

      alter user $(NEWUSER) quota unlimited on "USERS";

      select count(*) as doesuserexists from dba_users where username=UPPER('$(NEWUSER)');
    FORMAT = ORACLE_NONSPATIAL
    ORACLE_NONSPATIAL_SHOW_SYSTEM_TABLES = NO
    DATASET = $(ORACLEDB)
    ORACLE_NONSPATIAL_USE_UNIFIED_DATE_ATTRS = YES
    ORACLE_NONSPATIAL_PASSWORD = $(SYSPASS)
    COMBINE_GEOM = Initiator Geometry Only
    EXPOSED_ATTRIBUTE_LIST = doesuserexists
    ORACLE_NONSPATIAL_USER_NAME = $(SYSUSER)
    ORACLE_NONSPATIAL_QUERY_FEATURE_TYPES_FOR_MERGE_FILTERS = Yes
    RESULT -> SQLExecutor_CheckNewUser [INITIATOR]
    <REJECTED> -> UserDidNotGetCreated
Note: Tries to Connect as FME user
SQLExecutor_CheckNewUser
    ORACLE_NONSPATIAL_PERSISTENT_CONNECTION = YES
    ORACLE_NONSPATIAL_SERVER_TYPE = ORACLE8i
    COMBINE_ATTRS = Result Attributes Only
    ORACLE_NONSPATIAL_REMOVE_SCHEMA_QUALIFIER = NO
    SQL_STATEMENT = select 'user connected' as message from dual
    FORMAT = ORACLE_NONSPATIAL
    ORACLE_NONSPATIAL_SHOW_SYSTEM_TABLES = NO
    DATASET = $(ORACLEDB)
    ORACLE_NONSPATIAL_USE_UNIFIED_DATE_ATTRS = YES
    ORACLE_NONSPATIAL_PASSWORD = $(NEWUSER)
    COMBINE_GEOM = Initiator Geometry Only
    EXPOSED_ATTRIBUTE_LIST = message
    ORACLE_NONSPATIAL_USER_NAME = $(NEWUSER)
    ORACLE_NONSPATIAL_QUERY_FEATURE_TYPES_FOR_MERGE_FILTERS = Yes
    RESULT -> UserConnected
    <REJECTED> -> UserDidNotConnect
UserConnected: Logger
    MAXCOORDS = 1
    MAXFEATS = 1
    MESSAGE = Feature is:
    LOGGED -> SQLExecutor_CreateDataPumpDir [INITIATOR]
Note: Create new database directory / DPUMP_DIR1 as SYSTEM / pointing to c:/temp/datafiles / NOTE: Folder must exist
SQLExecutor_CreateDataPumpDir
    ORACLE_NONSPATIAL_PERSISTENT_CONNECTION = YES
    ORACLE_NONSPATIAL_SERVER_TYPE = ORACLE8i
    ORACLE_NONSPATIAL_REMOVE_SCHEMA_QUALIFIER = NO
    COMBINE_ATTRS = Result Attributes Only
    SQL_STATEMENT:
      FME_SQL_DELIMITER ?
      declare
       NewDirCreated VARCHAR(30) :='';
       mycount NUMBER := 0;
      begin
      select count(*) into mycount from all_directories where directory_name='DPUMP_DIR1';
          if mycount>0 then
              NewDirCreated := 'Directory Exists';
              DBMS_OUTPUT.put_line (NewDirCreated);

          Else
              execute immediate ('CREATE DIRECTORY DPUMP_DIR1 AS ''C:\FMEData2017\Resources\DatabaseWorkshop\OracleDataPump''');
              DBMS_OUTPUT.put_line ('Created New Directory - DPUMP_DIR1');
              NewDirCreated := 'Directory Created';
          end if;
      end;
      ?
      select count(*) as NewDirCreated from all_directories where directory_name='DPUMP_DIR1'?
    FORMAT = ORACLE_NONSPATIAL
    ORACLE_NONSPATIAL_SHOW_SYSTEM_TABLES = NO
    DATASET = $(ORACLEDB)
    ORACLE_NONSPATIAL_USE_UNIFIED_DATE_ATTRS = YES
    ORACLE_NONSPATIAL_PASSWORD = $(SYSPASS)
    COMBINE_GEOM = Initiator Geometry Only
    EXPOSED_ATTRIBUTE_LIST = NewDirCreated
    ORACLE_NONSPATIAL_QUERY_FEATURE_TYPES_FOR_MERGE_FILTERS = Yes
    ORACLE_NONSPATIAL_USER_NAME = $(SYSUSER)
    RESULT -> DataPumpDirCreated
    <REJECTED> -> DataPumpDirNotCreated
DataPumpDirCreated: Logger
    MAXCOORDS = 1
    MAXFEATS = 1
    MESSAGE = Feature is:
    LOGGED -> LoadDataPumpXE [SystemCaller_3_Input]
Note: TODO: / Need to add parameters to this
Note: impdp $(SYSUSER)/$(SYSPASS) DIRECTORY=DPUMP_DIR1 DUMPFILE=FMEUC.DMP LOGFILE=DPUMP_DIR1:FMEUC_imp.log REMAP_SCHEMA=FME:FME
LoadDataPumpXE
    SystemCaller_5_Output -> SQLExecutor [INITIATOR]
Note: Insert View SDO_GEOM_METADATA / (does not come in expdp)
SQLExecutor
    ORACLE_NONSPATIAL_PERSISTENT_CONNECTION = YES
    ORACLE_NONSPATIAL_SERVER_TYPE = ORACLE8i
    ORACLE_NONSPATIAL_REMOVE_SCHEMA_QUALIFIER = NO
    COMBINE_ATTRS = Result Attributes Only
    SQL_STATEMENT:
      FME_SQL_DELIMITER ;
      INSERT INTO USER_SDO_GEOM_METADATA (TABLE_NAME, COLUMN_NAME, DIMINFO, SRID)
      VALUES ('V_COUNTRIES_CA' ,'GEOM',
      MDSYS.SDO_DIM_ARRAY(MDSYS.SDO_DIM_ELEMENT('X',-180,180,0.05),MDSYS.SDO_DIM_ELEMENT('Y',-90,90,0.05)),4326) ;
      INSERT INTO USER_SDO_GEOM_METADATA (TABLE_NAME, COLUMN_NAME, DIMINFO, SRID)
      VALUES ('V_COUNTRIES_US' ,'GEOM',
      MDSYS.SDO_DIM_ARRAY(MDSYS.SDO_DIM_ELEMENT('X',-180,180,0.05),MDSYS.SDO_DIM_ELEMENT('Y',-90,90,0.05)),4326) ;
    FORMAT = ORACLE_NONSPATIAL
    ORACLE_NONSPATIAL_SHOW_SYSTEM_TABLES = NO
    DATASET = $(ORACLEDB)
    ORACLE_NONSPATIAL_USE_UNIFIED_DATE_ATTRS = YES
    ORACLE_NONSPATIAL_PASSWORD = $(NEWUSER)
    COMBINE_GEOM = Initiator Geometry Only
    ORACLE_NONSPATIAL_USER_NAME = $(NEWUSER)
    ORACLE_NONSPATIAL_QUERY_FEATURE_TYPES_FOR_MERGE_FILTERS = Yes
    RESULT -> SystemCaller_2
Note: Generate HTML Report / and Display to User
SystemCaller_2 [off]
DataPumpDirNotCreated: Logger
    MAXCOORDS = 1
    MAXFEATS = 1
    MESSAGE = Feature is:
UserDidNotConnect: Logger
    MAXCOORDS = 1
    MAXFEATS = 1
    MESSAGE = Feature is:
Note: v9 Moved datapump file and folder to C:\FMEData2017\Resources\DatabaseWorkshop\OracleDataPump from c:\temp\datafiles. / Assumes FMEUC.DMP exists in this folder.
UserDidNotGetCreated: Logger
    MAXCOORDS = 1
    MAXFEATS = 1
    MESSAGE = Feature is:

Bookmark: Implement Username Checks
AttributeCreator [off]
    ATTR_TABLE = SET_TO NewUserValue = $(NEWUSER)
    -> Tester [off]
Tester [off]
    TEST_MODE = Automatic
    BOOL_OP = OR
    TEST_CLAUSE:
      TEST NewUserValue NOT_ATTRIBUTE_IS_MISSING ""
      TEST @Value(NewUserValue) CONTAINS_REGEX \d
      TEST NewUserValue NOT_ATTRIBUTE_IS_EMPTY ""
      TEST NewUserValue NOT_ATTRIBUTE_VALUE_NULL ""
    TEST_DESCRIPTION = ""
    PASSED -> SQLExecutor_NewUser [INITIATOR]
    FAILED -> DontUseBlankUserName [off]
DontUseBlankUserName: Logger [off]
    MAXCOORDS = 1
    MAXFEATS = 1
    MESSAGE = Feature is:

FME custom transformer LoadDataPumpXE
Creates a batch file that sets the Oracle_Home to the Oracle XE libraries so it can call the impdp in the final SystemCaller.

SystemCaller_3_Input (input)
    -> SystemCaller_3
SystemCaller_3
    CMD = echo set ORACLE_HOME=C:\oraclexe\app\oracle\product\11.2.0\server>C:\FMEData2017\Resources\DatabaseWorkshop\OracleDataPump\impdp_command.bat
    -> SystemCaller_6
SystemCaller_6
    CMD = echo impdp SYSTEM/fmesys DIRECTORY=DPUMP_DIR1 DUMPFILE=FMEUC.DMP LOGFILE=DPUMP_DIR1:FMEUC_imp.log REMAP_SCHEMA=FME:FME>>C:\FMEData2017\Resources\DatabaseWorkshop\OracleDataPump\impdp_command.bat
    -> SystemCaller_5
SystemCaller_5
    CMD = C:\FMEData2017\Resources\DatabaseWorkshop\OracleDataPump\impdp_command.bat
    -> SystemCaller_5_Output (output)
SystemCaller_5_Output (output)
