FME workspace TrafficWorkOrders-SchoolZones-complete.fmw

Parameters:
- SourceDataset_CSV2 = $(FME_SHAREDRESOURCE_DATA)/Traffic Work Orders/Traffic_Signal_Work_Orders_Schools.csv   # Source CSV (Comma Separated Value) File(s)
- FME_SHAREDRESOURCE_DATA = C:\ProgramData\Safe Software\FMEFlow\resources\data   # FME Flow Data Directory

Readers:
- CSV2_1: CSV2 from $(SourceDataset_CSV2)

Writers:
- AUTOMATIONS_1: AUTOMATIONS

Note: Read Work Orders Dataset
CSV (reader CSV2_1)
    attributes: Work Order ID varchar(12), Status varchar(11), Asset Type varchar(35), Asset ID uint32, Location ID varchar(12), Created Date varchar(28), Modified Date varchar(28), Submitted Date varchar(28), Closed Date varchar(28), Fiscal Year uint32, Work Type varchar(14), Work Needed varchar(240), Work Type Other varchar(545), Work Requested By varchar(34), Job Description varchar(1073), Problem Found varchar(601), Action Taken varchar(2974), Follow-Up Needed varchar(5), Child Work Order varchar(12), Parent Work Order varchar(12), Is Follow-Up varchar(5), TMC Issue ID varchar(12), Service Request # varchar(14), Damage Report varchar(84), Location Name varchar(80), Latitude varchar(1), Longitude varchar(1), Location varchar(45)
    -> Tester
Note: Fetch school work orders that have not been Processed
Tester
    BOOL_OP = COMPOSITE
    COMPOSITE_TEST = 1 AND ( 2 OR 3 )
    TEST_CLAUSE:
      TEST @Value(Status) = Submitted
      TEST @Value(Asset Type) = School Beacon Zone
      TEST @Value(Asset Type) = School Beacon
    TEST_MODE = TEST
    PASSED -> AttributeKeeper
Note: Clean-up attributes to keep only those needed for processing
AttributeKeeper
    CREATE_BULK_MODE_FEATURES = NO
    KEEP_ATTRS = Asset ID,Asset Type,Job Description,Location,Problem Found,Service Request #,Work Needed,Work Order ID,Work Type
    -> WorkOrders (writer AUTOMATIONS_1)

Bookmark: FME Flow Automations Writer
Note: Send to Automation Writer for downstream processing
WorkOrders (writer AUTOMATIONS_1)
    attributes: Work Order ID string, Asset Type string, Asset ID int, Work Type string, Work Needed string, Job Description string, Problem Found string, Service Request # string, Location string
