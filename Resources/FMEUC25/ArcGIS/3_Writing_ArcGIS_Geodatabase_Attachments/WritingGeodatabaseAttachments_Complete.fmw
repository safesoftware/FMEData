FME workspace WritingGeodatabaseAttachments_Complete.fmw
Title: Writing Geodatabase Attachments - Complete

Parameters:
- SourceDataset_GML = $(FME_MF_DIR)Data\PointsOfInterest\POI.gml   # Source Geography Markup Language (GML) File(s)
- DestDataset_GEODATABASE_FILE_5 = $(FME_MF_DIR)Output\Attachments.gdb   # Destination Esri File Geodatabase
- SourceDataset_PATH_3 = $(FME_MF_DIR)Data\PointsOfInterest\Photos   # INCLUDE_WEB_BROWSER Source Folder and File Pathnames Folder

Readers:
- GML_1: GML from $(SourceDataset_GML)
- PATH_2: PATH from $(SourceDataset_PATH_3)

Writers:
- GEODATABASE_FILE_2: GEODATABASE_FILE to $(DestDataset_GEODATABASE_FILE_5)

CommunityCentres (reader GML_1)
    attributes: CentreName xml_char(30), CentreAddress xml_char(30), CentreURL xml_char(50), DocumentName xml_char(50), gml_pointProperty xml_geometry, gml_multiPointProperty xml_geometry
    -> AttributeManager
AttributeManager
    ATTR_TABLE:
      RENAME_SET_VALUE CentreName > Name (varchar(30))
      RENAME_SET_VALUE CentreAddress > Street (varchar(30))
      RENAME_SET_VALUE CentreURL > Website (varchar(50))
      RENAME_SET_VALUE DocumentName > Description (varchar(50))
      SET_TO PostalCode (varchar(200)) = unknown
    -> AttributeCreator
FireHalls (reader GML_1)
    attributes: HallNumber xml_char(30), Name xml_char(30), Address xml_char(30), PhoneNumber xml_char(30), Engine xml_char(1), Ladder xml_char(1), Quint xml_char(1), Rescue xml_char(1), Medic xml_char(1), DocumentName xml_char(50), gml_pointProperty xml_geometry, gml_multiPointProperty xml_geometry
    -> AttributeManager_2
AttributeManager_2
    ATTR_TABLE:
      RENAME_SET_VALUE HallNumber > Name (varchar(30))
      RENAME_SET_VALUE Name > Description (varchar(30))
      RENAME_SET_VALUE Address > Street (varchar(30))
    -> AttributeCreator
Libraries (reader GML_1)
    attributes: LibraryName xml_char(30), LibraryAddress xml_char(30), LibraryURL xml_char(50), DocumentName xml_char(50), gml_pointProperty xml_geometry, gml_multiPointProperty xml_geometry
    -> AttributeManager_3
AttributeManager_3
    ATTR_TABLE:
      RENAME_SET_VALUE LibraryName > Name (varchar(30))
      RENAME_SET_VALUE LibraryAddress > Street (varchar(30))
      RENAME_SET_VALUE LibraryURL > Website (varchar(50))
      RENAME_SET_VALUE DocumentName > Description (varchar(50))
      SET_TO PostalCode (varchar(200)) = unknown
    -> AttributeCreator
Note: geodb_feature_has_relationships
AttributeCreator
    ATTR_TABLE = SET_TO geodb_feature_has_relationships (varchar(200)) = yes
    -> Counter
Counter
    CNT_ATTR = geodb_oid
    SCOPE = Local
    START = 1
    -> AttributeRenamer
    -> AttributeRenamer_2
AttributeRenamer
    ATTR_TABLE = RENAME_SET_DEFAULT fme_feature_type > POIType
    KEEP_RENAMED_ONLY = no
    MISSING_INPUT_ATTRS = REMOVE
    -> GUIDGenerator
GUIDGenerator
    -> PointsOfInterest (writer GEODATABASE_FILE_2)
Note: geodb_rel_origin_oid
AttributeRenamer_2
    ATTR_TABLE = RENAME_SET_DEFAULT geodb_oid > geodb_rel_origin_oid
    KEEP_RENAMED_ONLY = no
    MISSING_INPUT_ATTRS = REMOVE
    -> FeatureMerger [REQUESTOR]
PATH (reader PATH_2)
    attributes: path_unix buffer, path_windows buffer, path_rootname buffer, path_filename buffer, path_extension buffer, path_filesize number(20,0), path_ownername buffer, path_readonly logical, path_modified_date datetime, path_created_date datetime, path_accessed_date datetime, path_directory_unix buffer, path_directory_windows buffer, path_type char(10)
    -> AttributeCreator_2
Note: geodb_feature_has_relationships
AttributeCreator_2
    ATTR_TABLE = SET_TO geodb_feature_has_relationships (varchar(200)) = yes
    -> Counter_2
Counter_2
    CNT_ATTR = geodb_oid
    SCOPE = Local
    START = 1
    -> AttributeRenamer_3
    -> AttributeCopier
Note: geodb_rel_destination_oid
AttributeRenamer_3
    ATTR_TABLE = RENAME_SET_DEFAULT geodb_oid > geodb_rel_destination_oid
    KEEP_RENAMED_ONLY = no
    MISSING_INPUT_ATTRS = REMOVE
    -> FeatureMerger [SUPPLIER]
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Name) @Value(path_rootname) AUTO
    LIST_ATTRS_TO_INCLUDE = geodb_rel_destination_oid path_filename
    LIST_NAME = Docs
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> ListExploder
ListExploder
    ATTR_CONFLICT_RES_LOOKUP = INCOMING_IF_CONFLICT
    INDEX_ATTR = _element_index
    LIST_ATTR = Docs{}
    ATTR_ACCUM_MODE = Merge List Attributes
    ATTR_CONFLICT_RES = Use List Attribute Values
    ELEMENTS -> AttributeCreator_3
Note: geodb_relationship
AttributeCreator_3
    ATTR_TABLE = SET_TO geodb_type (varchar(200)) = geodb_relationship
    -> PointsOfInterest__ATTACHREL (writer GEODATABASE_FILE_2)
AttributeCopier
    ATTR_TABLE:
      COPY geodb_oid > REL_OBJECTID
      COPY path_filename > ATT_NAME
      COPY path_filesize > DATA_SIZE
      COPY path_extension > CONTENT_TYPE
    MISSING_INPUT_ATTRS = PRESERVE
    -> StringConcatenator
StringConcatenator
    ACTION = Create New Attribute
    PARM_LINE = fme_basicstring:8%22:image/p.@Value(path_extension)
    VAL_ATTR = CONTENT_TYPE
    -> AttributeFileReader
AttributeFileReader
    CHAR_ENCODING = fme-binary
    DEST_ATTR = DATA
    FILE_NAME = @Value(path_windows)
    -> PointsOfInterest__ATTACH (writer GEODATABASE_FILE_2)

Bookmark: Output geodatabase
Note: Output points
PointsOfInterest (writer GEODATABASE_FILE_2)
    attributes: OBJECTID integer, Name char(50), POIType char(50), Street char(50), City char(50), State char(5), Country char(50), PostalCode char(7), Description char(100), PhoneNumber char(10), Website char(80), GFID char(38)
PointsOfInterest__ATTACHREL (writer GEODATABASE_FILE_2)
Note: Output table
PointsOfInterest__ATTACH (writer GEODATABASE_FILE_2)
    attributes: OBJECTID integer, ATTACHMENTID integer, REL_OBJECTID integer, CONTENT_TYPE char(150), ATT_NAME char(250), DATA_SIZE integer, DATA blob
