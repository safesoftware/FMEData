FME workspace AddressesToNotify-SelfServe.fmw
Title: AddressesToNotify-SelfServe

Parameters:
- SourceDataset_SHAPEFILE = $(FME_MF_DIR)Data\water_service_area.shp   # Service Areas Input Shapefile Dataset
- SERVICE_DATE =   # Date of Water Service
- DestDataset_XLSXW = .\Output\AddressesToNotify.xlsx   # Destination Microsoft Excel File

Readers:
- CSV2_2: CSV2 from $(FME_MF_DIR)Data\LocalAddresses.csv in LL-WGS84
- SHAPEFILE_1: SHAPEFILE from $(SourceDataset_SHAPEFILE)

Writers:
- XLSXW_1: XLSXW to $(DestDataset_XLSXW) in LL84

Note: CSV: LocalAddresses [CSV2]
CSV (reader CSV2_2)
    attributes: FULL_ADDRESS varchar(33), LOCALITY varchar(6), LONGITUDE x_coordinate, LATITUDE y_coordinate
    -> SpatialFilter [Candidate]
Note: water_service_area [SHAPEFILE]
water_service_area (reader SHAPEFILE_1)
    attributes: HGL varchar(254), NAME varchar(254), STATUS varchar(254)
    -> Tester
Note: Status = Red
Tester
    BOOL_OP = OR
    TEST_CLAUSE = TEST @Value(STATUS) = RED
    TEST_MODE = TEST
    PASSED -> SpatialFilter [Filter]
Note: Spatial Predicate: Filter OGC-Intersects Candidate
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
Note: Rename LOCALITY to CITY and remove _predicate attribute
AttributeManager
    ATTR_TABLE:
      RENAME_SET_VALUE LOCALITY > CITY (varchar(6))
      REMOVE _predicate (buffer)
      SET_TO SERVICE_DATE (date) = $(SERVICE_DATE)
    -> Addresses (writer XLSXW_1)
Note: Addresses: AddressesToNotify [XLSXW]
Addresses (writer XLSXW_1)
    attributes: FULL_ADDRESS string(33), CITY string(6), LONGITUDE number(20), LATITUDE number(20), HGL string(254), NAME string(254), STATUS string(254), SERVICE_DATE date(20)
