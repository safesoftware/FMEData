FME workspace 5.TransformingLinesIntoBoxes.fmw

Parameters:
- SourceDataset_JPEG = C:\FMEData\Resources\FMEUC25\AugmentedReality\Data\manholecover.jpg   # Source JPEG File(s)
- SourceDataset_JPEG_3 = C:\FMEData\Resources\FMEUC25\AugmentedReality\Data\catchbasin.jpg   # Source JPEG File(s)

Readers:
- JPEG_1: JPEG from $(SourceDataset_JPEG)
- JPEG_2: JPEG from $(SourceDataset_JPEG_3)

Creator
    GEOM = <?xml version="1.0" encoding="US_ASCII" standalone="no" ?><geometry><point><coord x="1.5" y="0"/></point></geometry>
    GEOMTYPE = Geometry Object
    NUM = 1
    CREATED -> FeatureReader [INITIATOR]
FeatureReader
    ATTRIBUTES = ElectricalCables,"ID,Status,Material,Installed,LastInspection,LastMaintenance,LastRepair,Width,Height,VoltageRating,Condition,fme_feature_type",FireHydrant,"ID,Status,Installed,LastInspection,LastMaintenance,LastRepair,Name,Model,Material,MaxPressure,Height,OutletSize,TemperatureRange,FlowRate,Weight,fme_feature_type",HydrantFeed,"ID,Status,Installed,LastInspection,LastMaintenance,LastRepair,Diameter,FlowCapacity,Depth,MaterialCondition,PressureRating,Ownership,fme_feature_type",RoadCenterlines,"ID,Status,FullName,Type,Lanes,Surface,SpeedLimit,fme_feature_type",SewerMain,"ID,Status,Material,Installed,LastInspection,LastMaintenance,LastRepair,CrossRisk,Diameter,Depth,FlowCapacity,MaterialCondition,Ownership,PressureRating,Grade,UpElevation,DownElevation,Length,fme_feature_type",SewerServiceConnection,"ID,Status,Material,Installed,LastInspection,LastMaintenance,LastRepair,Diameter,Depth,FlowCapacity,MaterialCondition,Ownership,PressureRating,UpElevation,DownElevation,Length,Grade,fme_feature_type",StormCatchBasin,"ID,Status,Installed,LastInspection,LastMaintenance,LastRepair,Diameter,FlowCapacity,Depth,MaterialCondition,SedimentLevel,Ownership,Width,Length,fme_feature_type",StormMain,"ID,Status,Material,Installed,LastInspection,LastMaintenance,LastRepair,Diameter,FlowCapacity,Depth,MaterialCondition,PressureRating,Ownership,Length,UpElevation,DownElevation,Grade,fme_feature_type",UtilityPole,"ID,Status,Material,Installed,LastInspection,LastMaintenance,LastRepair,Height,Diameter,Condition,Ownership,fme_feature_type",WaterMain,"ID,Status,Type,Installed,LastInspection,LastMaintenance,LastRepair,Diameter,FlowCapacity,Depth,MaterialCondition,PressureRating,Ownership,fme_feature_type",WaterServiceConnection,"ID,Status,Material,Installed,LastInspection,LastMaintenance,LastRepair,Diameter,ParcelID,FlowCapacity,Depth,MaterialCondition,PressureRating,Ownership,fme_feature_type",WaterValve,"ID,Status,Installed,LastInspection,LastMaintenance,LastRepair,MaterialCondition,Ownership,fme_feature_type",WaterValveCover,"ID,Status,Installed,LastInspection,LastMaintenance,LastRepair,Diameter,Depth,fme_feature_type"
    ATTR_ACCUM_MODE = Only Use Result
    CLIP_TO_ENVELOPE = NO
    COMBINE_GEOM = Use Result
    DATASET = C:\FMEData\Resources\FMEUC25\AugmentedReality\Data\UndergroundInfrastructureNew.sqlite
    FEATURETYPES = ElectricalCables FireHydrant HydrantFeed RoadCenterlines SewerMain SewerServiceConnection StormCatchBasin StormMain UtilityPole WaterMain WaterServiceConnection WaterValve WaterValveCover
    FORMAT = SPATIALITE_NATIVE
    GEOMETRY_TYPES = ElectricalCables,"""geom,fme_line""",FireHydrant,"""geom,fme_point""",HydrantFeed,"""geom,fme_line""",RoadCenterlines,"""geom,fme_line""",SewerMain,"""geom,fme_line""",SewerServiceConnection,"""geom,fme_line""",StormCatchBasin,"""geom,fme_point""",StormMain,"""geom,fme_line""",UtilityPole,"""geom,fme_point""",WaterMain,"""geom,fme_line""",WaterServiceConnection,"""geom,fme_line""",WaterValve,"""geom,fme_point""",WaterValveCover,"""geom,fme_point"""
    INITIATOR_FIRST_OUTPUT = default
    INTERACT = NONE
    ORDER_RESULTS = No
    OUTPUT_ADD_SCHEMA_ATTRIBUTES = NO
    OUTPUT_FEATURES_DISPLAY = Schema and Data Features
    SPATIALITE_NATIVE_CREATE_FEATURE_TABLES_FROM_DATA = No
    SPATIALITE_NATIVE_IGNORE_METADATA_TABLES = YES
    SPATIALITE_NATIVE_QUERY_FEATURE_TYPES_FOR_MERGE_FILTERS = Yes
    SPATIALITE_NATIVE_SPATIALITE_NATIVE_EXPOSE_FORMAT_ATTRS = fme_feature_type,varchar(50)
    SPATIALITE_NATIVE_SUPPORT_INTERNATIONALIZATION = YES
    SPATIALITE_NATIVE_USE_SEARCH_ENVELOPE = NO
    ElectricalCables -> Bufferer
    FireHydrant -> CoordinateExtractor_2
    HydrantFeed -> PipeReplacer_2
    SewerMain -> PipeReplacer_3
    SewerServiceConnection -> PipeReplacer_3
    StormCatchBasin -> CoordinateExtractor
    StormMain -> PipeReplacer_4
    UtilityPole -> 2DEllipseReplacer
    WaterMain -> PipeReplacer
    WaterServiceConnection -> PipeReplacer_2
    WaterValve -> CoordinateExtractor_3
    WaterValveCover -> 2DEllipseReplacer_2

Bookmark: Fire Hydrant
CoordinateExtractor_2
    IND = 0
    RECURSIVE = No
    X_ATTR = _x
    Y_ATTR = _y
    Z_ATTR = _z
    MODE = Specify Coordinate
    -> FeatureReader_2 [INITIATOR]
FeatureReader_2
    ATTRIBUTES = Hydrant0,
    ATTR_ACCUM_MODE = Merge Initiator and Result
    ATTR_CONFLICT_RES = Use Result
    ATTR_IGNORE_NULLS = No
    CLIP_TO_ENVELOPE = NO
    COMBINE_GEOM = Use Result
    DATASET = C:\FMEData\Resources\FMEUC25\AugmentedReality\Data\FireHydrant0.zip
    FORMAT = OBJ
    GEOMETRY_TYPES = Hydrant0,""",fme_collection,fme_line,fme_point,fme_surface"""
    INITIATOR_FIRST_OUTPUT = default
    INTERACT = NONE
    OBJ_MERGE_MESH_PARTS = No
    OBJ_MOVE_TO_WORLD_COORDSYS = Yes
    OBJ_USE_SEARCH_ENVELOPE = NO
    OBJ_VARIABLE_FEATURE_TYPES = yes
    ORDER_RESULTS = No
    OUTPUT_ADD_SCHEMA_ATTRIBUTES = NO
    OUTPUT_FEATURES_DISPLAY = Schema and Data Features
    Hydrant0 -> Offsetter_2
Offsetter_2
    MODE_LOOKUP = CARTESIAN
    XOFF = @Value(_x)
    YOFF = @Value(_y)
    ZOFF = 0
    MODE = Cartesian Coordinate

Bookmark: Storm water
CoordinateExtractor
    IND = 0
    RECURSIVE = No
    X_ATTR = _x
    Y_ATTR = _y
    Z_ATTR = _z
    MODE = Specify Coordinate
    -> 2DBoxReplacer
2DBoxReplacer
    MAXXVALATTR = 0.3
    MAXYVALATTR = 0.2
    MINXVALATTR = -0.3
    MINYVALATTR = -0.2
    BOX -> Offsetter
Offsetter
    MODE_LOOKUP = CARTESIAN
    XOFF = @Value(_x)
    YOFF = @Value(_y)
    ZOFF = 0
    MODE = Cartesian Coordinate
    OFFSET -> Extruder_3
Extruder_3
    DIRECTION_LOOKUP = AUTO
    DISTANCE = 0.03
    DIRECTION = Auto
    EXTRUDED -> AppearanceSetter_3 [GEOMETRY]
PipeReplacer_4
    INNER_RADIUS = @Value(Diameter)/2*0.9
    OUTER_RADIUS = @Value(Diameter)/2
    -> VertexNormalGenerator_4
VertexNormalGenerator_4
    VERTEX_NORM_MODE = AVERAGED
    -> AppearanceSetter_7 [GEOMETRY]
AppearanceSetter_7
    AMBIENT_COLOR = 0,0.588235,1
    APPEARANCE_DEFINITION_STORAGE = CREATE
    APPEARANCE_NAME = Water
    DIFFUSE_COLOR = 0,0.329412,0.576471
    GQUERY:
      for $geom in //geometry
      where $geom/count(parent::geometry) = 0
      return number($geom/@fme_id)
    SHININESS = 0.8
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
JPEG (reader JPEG_2)
    -> AppearanceSetter_3 [APPEARANCE]
AppearanceSetter_3
    APPEARANCE_DEFINITION_STORAGE = CREATE
    APPEARANCE_NAME = CatchBasin
    GQUERY:
      for $geom in //geometry
      where $geom/count(parent::geometry) = 0
      return number($geom/@fme_id)
    SIDE_OPTION = BOTH
    TEXTURE_MAPPING_TYPE = XY_PLANE
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = From Top View
    USE_EXISTING_TEXTURE_COORDINATES = No

Bookmark: Electrical
2DEllipseReplacer
    PRIMAXIS = @Value(Diameter)/2
    ROT = 0
    SECAXIS = @Value(Diameter)/2
    ELLIPSE -> Extruder
Extruder
    DIRECTION_LOOKUP = AUTO
    DISTANCE = @Value(Height)
    DIRECTION = Auto
    EXTRUDED -> AppearanceSetter [GEOMETRY]
Bufferer
    ANGLE = 22.5
    CAP_STYLE_LOOKUP = CAP_PROJECTING
    CORNER_STYLE_LOOKUP = JOIN_ARC
    MODE = AREA
    OFFSET = @Value(Width)/2
    OFFSET_UNITS = NONE
    PRECISION = APPROX
    CAP_STYLE = Square
    CORNER_STYLE = Arc
    BUFFERED -> Extruder_4
Extruder_4
    DIRECTION_LOOKUP = AUTO
    DISTANCE = @Value(Height)
    DIRECTION = Auto
    EXTRUDED -> VertexNormalGenerator_5
VertexNormalGenerator_5
    VERTEX_NORM_MODE = FACET
    -> AppearanceSetter [GEOMETRY]
AppearanceSetter
    AMBIENT_COLOR = 1,0.576471,0
    APPEARANCE_DEFINITION_STORAGE = CREATE
    APPEARANCE_NAME = Electrical
    DIFFUSE_COLOR = 1,0.988235,0.47451
    GQUERY:
      for $geom in //geometry
      where $geom/count(parent::geometry) = 0
      return number($geom/@fme_id)
    SHININESS = 0.8
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No

Bookmark: Sewage
PipeReplacer_3
    INNER_RADIUS = @Value(Diameter)/2*0.9
    OUTER_RADIUS = @Value(Diameter)/2
    -> VertexNormalGenerator_3
VertexNormalGenerator_3
    VERTEX_NORM_MODE = AVERAGED
    -> AppearanceSetter_6 [GEOMETRY]
AppearanceSetter_6
    AMBIENT_COLOR = 0.843137,0.513725,1
    APPEARANCE_DEFINITION_STORAGE = CREATE
    APPEARANCE_NAME = Water
    DIFFUSE_COLOR = 0.580392,0.129412,0.576471
    GQUERY:
      for $geom in //geometry
      where $geom/count(parent::geometry) = 0
      return number($geom/@fme_id)
    SHININESS = 0.8
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No

Bookmark: Water
PipeReplacer
    INNER_RADIUS = @Value(Diameter)/2*0.9
    OUTER_RADIUS = @Value(Diameter)/2
    -> VertexNormalGenerator
VertexNormalGenerator
    VERTEX_NORM_MODE = AVERAGED
    -> AppearanceSetter_4 [GEOMETRY]
AppearanceSetter_4
    AMBIENT_COLOR = 0,0.992157,1
    APPEARANCE_DEFINITION_STORAGE = CREATE
    APPEARANCE_NAME = Water
    DIFFUSE_COLOR = 0,0.588235,1
    GQUERY:
      for $geom in //geometry
      where $geom/count(parent::geometry) = 0
      return number($geom/@fme_id)
    SHININESS = 0.8
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
PipeReplacer_2
    INNER_RADIUS = @Value(Diameter)/2*0.9
    OUTER_RADIUS = @Value(Diameter)/2
    -> VertexNormalGenerator_2
VertexNormalGenerator_2
    VERTEX_NORM_MODE = AVERAGED
    -> AppearanceSetter_5 [GEOMETRY]
AppearanceSetter_5
    AMBIENT_COLOR = 0,0.992157,1
    APPEARANCE_DEFINITION_STORAGE = CREATE
    APPEARANCE_NAME = Water
    DIFFUSE_COLOR = 0,0.588235,1
    GQUERY:
      for $geom in //geometry
      where $geom/count(parent::geometry) = 0
      return number($geom/@fme_id)
    SHININESS = 0.8
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
CoordinateExtractor_3
    IND = 0
    RECURSIVE = No
    X_ATTR = _x
    Y_ATTR = _y
    Z_ATTR = _z
    MODE = Specify Coordinate
    -> FeatureReader_3 [INITIATOR]
FeatureReader_3
    ATTRIBUTES = WaterValve,
    ATTR_ACCUM_MODE = Merge Initiator and Result
    ATTR_CONFLICT_RES = Use Result
    ATTR_IGNORE_NULLS = No
    CLIP_TO_ENVELOPE = NO
    COMBINE_GEOM = Use Result
    DATASET = C:\FMEData\Resources\FMEUC25\AugmentedReality\Data\WaterValve.zip
    FORMAT = OBJ
    GEOMETRY_TYPES = WaterValve,""",fme_collection,fme_line,fme_point,fme_surface"""
    INITIATOR_FIRST_OUTPUT = default
    INTERACT = NONE
    OBJ_MERGE_MESH_PARTS = No
    OBJ_MOVE_TO_WORLD_COORDSYS = Yes
    OBJ_USE_SEARCH_ENVELOPE = NO
    OBJ_VARIABLE_FEATURE_TYPES = yes
    ORDER_RESULTS = No
    OUTPUT_ADD_SCHEMA_ATTRIBUTES = NO
    OUTPUT_FEATURES_DISPLAY = Schema and Data Features
    WaterValve -> Offsetter_3
Offsetter_3
    MODE_LOOKUP = CARTESIAN
    XOFF = @Value(_x)
    YOFF = @Value(_y)
    ZOFF = 0
    MODE = Cartesian Coordinate
2DEllipseReplacer_2
    PRIMAXIS = @Value(Diameter)/2
    ROT = 0
    SECAXIS = @Value(Diameter)/2
    ELLIPSE -> Extruder_2
Extruder_2
    DIRECTION_LOOKUP = AUTO
    DISTANCE = 0.05
    DIRECTION = Auto
    EXTRUDED -> AppearanceSetter_2 [GEOMETRY]
JPEG (reader JPEG_1)
    -> AppearanceSetter_2 [APPEARANCE]
AppearanceSetter_2
    APPEARANCE_DEFINITION_STORAGE = CREATE
    APPEARANCE_NAME = ManholeCover
    GQUERY:
      for $geom in //geometry
      where $geom/count(parent::geometry) = 0
      return number($geom/@fme_id)
    SIDE_OPTION = BOTH
    TEXTURE_MAPPING_TYPE = XY_PLANE
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = From Top View
    USE_EXISTING_TEXTURE_COORDINATES = No
