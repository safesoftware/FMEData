FME workspace Complete Workspace - Part 1.fmw
Title: KAFKA to POSTGIS

Parameters:
- DestDataset_MSSQL_SPATIAL = Localhost FMEData   # SQL Server Connection

Writers:
- MSSQL_SPATIAL_1: MSSQL_SPATIAL to $(DestDataset_MSSQL_SPATIAL)

Creator
    GEOMTYPE = Geometry Object
    NUM = 1
    CREATED -> KafkaConnector
Note: Trucks only
Tester
    BOOL_OP = OR
    TEST_CLAUSE = TEST @Value(vehicle_type) = trucks
    TEST_MODE = TEST
    PASSED -> GeometryReplacer
Note: Clean up attributes
AttributeManager
    ATTR_TABLE:
      REMOVE _creation_instance (uint64)
      REMOVE _value (buffer)
      REMOVE _timestamp (buffer)
      REMOVE _connector_id (buffer)
      REMOVE timestamp (buffer)
    -> TruckFleetStream (writer MSSQL_SPATIAL_1)
Note: Write to database (SQL Server)
TruckFleetStream (writer MSSQL_SPATIAL_1)
    attributes: _topic varchar_max, vehicle_id varchar_max, vehicle_category varchar_max, vehicle_type varchar_max

Bookmark: Connect to Kafka, receive message from topic, parse message
KafkaConnector
    __kafka_action_multiparam = __kafka_topics_list][{"display":"cov-fleet-location","value":"cov-fleet-location"}]]__kafka_receive_mode]batch]__kafka_max_messages]<Unused>]__kafka_batch_size]1000]__kafka_consumer_group_id]simulate-geofence]__kafka_starting_offset]earliest]__kafka_partition]<Unused>]__kafka_custom_offset]<Unused>]__kafka_auto_commit]YES]__kafka_heartbeat_group]<Unused>]__kafka_heartbeat_interval]<Unused>]__kafka_heartbeat_time_unit]<Unused>]__kafka_advanced_options_group]FME_DISCLOSURE_CLOSED]__kafka_advanced_options]]__kafka_message_options_group]FME_DISCLOSURE_OPEN]__kafka_message_schema]simple]__kafka_value_encoding]utf-8]__kafka_schema_registry]<Unused>]__kafka_attributes_to_add]"_value _timestamp _topic"]FME_CONTROLLER_QUERY_FILE]kafka_deps/Receive.fme]FME_CONTROLLER_CHOICE]Receive
    __kafka_brokers_list = pkc-4nym6.us-east-1.aws.confluent.cloud:9092
    __kafka_connection = administrator Apache Kafka (safe.kafka)
    __kafka_credential_source = webconn
    __kafka_operation_type = Receive
    __kafka_sasl_mechanisms = PLAIN
    __kafka_security_protocol = SASL_SSL
    -> JSONFlattener
JSONFlattener
    ERROR_LIST_ATTR = _json_error
    JSON_DOCUMENT = @Value(_value)
    NEW_ATTRIBUTES = vehicle_id buffer timestamp buffer vehicle_category buffer vehicle_type buffer geo buffer
    READ_FROM_FILE = NO
    RECURSIVE = YES
    -> Tester

Bookmark: Create Geometry
GeometryReplacer
    KIND = wkt
    OGC_WKT_PRECISION = FLOAT_64
    REMOVE_ATTRIBUTE = Yes
    SOURCE = @Value(geo)
    KIND_LONG = OGC Well Known Text
    OGC_WKT_PRECISION_DISPLAY = 64-bit
    -> CoordinateSystemSetter
CoordinateSystemSetter
    COORDSYS = LL84
    -> AttributeManager
