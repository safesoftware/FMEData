FME workspace WOTask.fmw

Parameters:
- _webhook_message = {"Address":"1234%20Fake%20St.", "WorkOrderId":"295"}   # Webhook Message

Writers:
- AUTOMATIONS_1: AUTOMATIONS

Creator
    GEOMTYPE = Geometry Object
    NUM = 1
    CREATED -> ParameterFetcher
ParameterFetcher
    ATTR_LIST = __webhook_message $(_webhook_message)
    -> JSONFlattener
JSONFlattener
    ERROR_LIST_ATTR = _json_error
    JSON_DOCUMENT = @Value(__webhook_message)
    NEW_ATTRIBUTES = Address WorkOrderId
    READ_FROM_FILE = NO
    RECURSIVE = Yes
    -> TextDecoder
TextDecoder
    DEST_ATTR = Address
    ENCODING_TYPE = URL (Percent Encoding)
    STRING_TO_DECODE = @Value(Address)
    -> HTTPCaller
Note: Please change the request URL and web connection to match your instance and credentials. / You may need to navigate to FME Options > Web Connections to create a new Cityworks connection.
HTTPCaller
    ADDITIONAL_URL_PARAMETERS = data;{"WorkOrderId":"@Value(WorkOrderId)", "WorkOrderSid":@Value(WorkOrderId),"SequenceId":1,"TaskSids":[4],"Comments":"@Value(Address)"}
    AUTH_METHOD = Web Connection
    AUTH_NAMED_CONNECTION = Nathan Cityworks Training
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = http://ec2-44-226-87-139.us-west-2.compute.amazonaws.com/cityworks/services/Ams/Tasks/Add
    TRANSFER_TIMEOUT_LENGTH = 90
    UPLOAD_CONTENT_TYPE = JSON (application/json)
    UPLOAD_TYPE = Specify Upload Body
    USE_COOKIES = No
    VERIFY_SSL_CERTIFICATES = Yes
    -> JSONFormatter
JSONFormatter
    ERROR_LIST_ATTR = _json_error
    FORMAT = Pretty Print
    INDENT_STYLE = 3 spaces
    JSON_DOCUMENT = @Value(_response_body)
    OUTPUT_ATTR = _formatted
    OUTPUT_ENCODING = UTF-8
    READ_FROM_FILE = NO
    REMOVE_EMPTY_OBJECTS_AND_ARRAYS = No
    REMOVE_EMPTY_STRINGS = No
    REMOVE_NULLS = No
    -> JSONExtractor
JSONExtractor
    EXTRACT_QUERY_TABLE = WOTaskId json["Value"][*]["WOTaskId"] TaskName json["Value"][*]["TaskName"] Description json["Value"][*]["Description"]
    JSON_DOCUMENT = @Value(_response_body)
    READ_FROM_FILE = NO
    EVALUATED -> Work Order Task (writer AUTOMATIONS_1)
Work Order Task (writer AUTOMATIONS_1)
    attributes: _creation_instance string, __webhook_message string, Address string, WorkOrderId string, _response_body string, _http_status_code string, _formatted string, WOTaskId string, TaskName string, Description string
