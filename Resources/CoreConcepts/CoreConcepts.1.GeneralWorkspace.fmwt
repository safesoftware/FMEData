FME workspace CoreConcepts.1.GeneralWorkspace.fmwt
Title: CoreConcepts.1.GeneralWorkspace
Description: A general workspace that demonstrates the flow of single features

Parameters:
- SourceDataset_ESRISHAPE = $(FME_MF_DIR)1/Addresses/People.shp   # Source Esri Shapefile(s)
- DestDataset_ESRISHAPE = C:\FMEData2017\Output\Training   # Destination Esri Shapefile Folder

Readers:
- ESRISHAPE_1: ESRISHAPE from $(SourceDataset_ESRISHAPE)

Writers:
- ESRISHAPE_2: ESRISHAPE to $(DestDataset_ESRISHAPE)

Note: Read a List of People
People (reader ESRISHAPE_1)
    attributes: Name char(200), Gender char(200)
    -> Junction
Junction
    -> Tester
Note: Test for Gender=F
Tester
    TEST_MODE = Automatic
    TEST_CLAUSE = TEST @Value(Gender) = F
    TEST_DESCRIPTION = ""
    BOOL_OP = OR
    PASSED -> LengthCalculator
Note: Measure Height
LengthCalculator
    LEN_ATTR = Height
    MULT = 1
    DIM = 2
    -> People (writer ESRISHAPE_2)
Note: Write a New List of People
People (writer ESRISHAPE_2)
    attributes: Name char(200), Gender char(200), Height float
