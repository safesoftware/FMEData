FME workspace ReadIFC_final.fmw

Parameters:
- SourceDataset_IFC = c:\FMEData\Resources\FMEUC22\Working with BIM Data\Data\Duplex_A.ifc   # Source Industry Foundation Class (IFC) File(s)
- FEATURE_TYPES =

Readers:
- IFC_1: IFC from $(SourceDataset_IFC)

IfcBeam (reader IFC_1)
    attributes: GlobalId char(22), Name string, Description string, ObjectType string, Tag string, ApplicableOccurrence string, BuildingAddress.AddressLines string, BuildingAddress.Country string, BuildingAddress.Description string, BuildingAddress.InternalLocation string, BuildingAddress.PostalBox string, BuildingAddress.PostalCode string, BuildingAddress.Purpose enumeration, BuildingAddress.Region string, BuildingAddress.Town string, BuildingAddress.UserDefinedPurpose string, CompositionType string, ElementType string, Elevation real, ElevationOfRefHeight real, ElevationOfTerrain real, ElevationWithFlooring real, InteriorOrExteriorSpace enumeration, LandTitleNumber string, LongName string, NumberOfRiser int, NumberOfTreads int, OverallHeight real, OverallWidth real, Phase string,
      PredefinedType enumeration, RefElevation real, RefLatitude real, RefLongitude real, RiserHeight real, ShapeType enumeration, SiteAddress.AddressLines string, SiteAddress.Country string, SiteAddress.Description string, SiteAddress.InternalLocation string, SiteAddress.PostalBox string, SiteAddress.PostalCode string, SiteAddress.Purpose enumeration, SiteAddress.Region string, SiteAddress.Town string, SiteAddress.UserDefinedPurpose string, TreadLength real, ifc_type_name string, ifc_type_object_id string
    -> GeometryPropertyExtractor
GeometryPropertyExtractor
    EXTRACTTYPE_PARAM = Traits
    PREFIX_EXTRACTED_TRAITS = Yes
    EXTRACTED -> AttributeExposer
AttributeExposer
    ATTR_LIST =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
    -> GeometryPartExtractor
GeometryPartExtractor
    GQUERY:
      for $geom in //geometry
      where $geom/@fme_geometry_name = 'Body'
      and $geom/parent::geometry/count(parent::geometry) = 0
      return number($geom/@fme_id)
    EXTRACTED -> Inspector
Inspector
