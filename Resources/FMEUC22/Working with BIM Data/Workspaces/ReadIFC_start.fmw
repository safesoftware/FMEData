FME workspace ReadIFC_start.fmw

Parameters:
- SourceDataset_IFC = c:\FMEData\Resources\FMEUC22\Working with BIM Data\Data\Duplex_A.ifc   # Source Industry Foundation Class (IFC) File(s)
- FEATURE_TYPES =

Readers:
- IFC_2: IFC from $(SourceDataset_IFC)

IfcBeam (reader IFC_2)
    attributes: GlobalId char(22), Name string, Description string, ObjectType string, Tag string, ApplicableOccurrence string, BuildingAddress.AddressLines string, BuildingAddress.Country string, BuildingAddress.Description string, BuildingAddress.InternalLocation string, BuildingAddress.PostalBox string, BuildingAddress.PostalCode string, BuildingAddress.Purpose enumeration, BuildingAddress.Region string, BuildingAddress.Town string, BuildingAddress.UserDefinedPurpose string, CompositionType string, ElementType string, Elevation real, ElevationOfRefHeight real, ElevationOfTerrain real, ElevationWithFlooring real, InteriorOrExteriorSpace enumeration, LandTitleNumber string, LongName string, NumberOfRiser int, NumberOfTreads int, OverallHeight real, OverallWidth real, Phase string,
      PredefinedType enumeration, RefElevation real, RefLatitude real, RefLongitude real, RiserHeight real, ShapeType enumeration, SiteAddress.AddressLines string, SiteAddress.Country string, SiteAddress.Description string, SiteAddress.InternalLocation string, SiteAddress.PostalBox string, SiteAddress.PostalCode string, SiteAddress.Purpose enumeration, SiteAddress.Region string, SiteAddress.Town string, SiteAddress.UserDefinedPurpose string, TreadLength real, ifc_type_name string, ifc_type_object_id string
    -> Inspector
Inspector
