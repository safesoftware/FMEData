FME workspace Exercise2-Final-ListAttributeHandling.fmwt
Title: CSV2 to OGCGEOPACKAGE

Parameters:
- SourceDataset_CSV2_3 = $(FME_MF_DIR)sourceData/CellTowersGreaterVancouver.csv   # Source CSV (Comma Separated Value) File(s)
- DestDataset_OGCGEOPACKAGE = $(FME_MF_DIR)results\CellTowers.gpkg   # GeoPackage File

Readers:
- CSV2_2: CSV2 from $(SourceDataset_CSV2_3)

Writers:
- OGCGEOPACKAGE_1: OGCGEOPACKAGE to $(DestDataset_OGCGEOPACKAGE) in UTM84-10N

Note: formated the date time in the CSV reader parameters or use DateTimeConverter
CSV (reader CSV2_2)
    attributes: RECORDID uint32, NEW_ACCOUNT uint64, NEW_LICNO varchar(14), OLD_ACCOUNT real64, OLD_LICNO varchar(11), LICENSEE varchar(34), SERVICE varchar(6), TRANSMIT_FREQ real32, RECEIVE_FREQ real32, TRANSMIT_LOWER real32, TRANSMIT_UPPER real32, TRANSMIT_BW real32, LOCATION varchar(41), PROV varchar(3), LATITUDE y_coordinate, LONGITUDE x_coordinate, SITE_ELEV z_coordinate, STUCT_HT real32, TX_MFR varchar(3), TX_MODEL varchar(1), TX_PWR real64, TX_PWR_TYPE varchar(2), BW_EMISSION varchar(11), TX_ANT_MFR varchar(3), TX_ANT_MODEL varchar(40), TX_ANT_HT real32, TX_ANT_AZIM real32, TX_ANT_ELEV_ANGLE real32, TX_ANT_GAIN real32, TX_ANT_DIRECTIONAL varchar(2),
      TX_LINE_LOSS real32, ZONE_ENHANCER varchar(3), LAST_MOD_DATE datetime, LAST_UPLOAD_DATE datetime
    -> BulkAttributeRenamer
    -> NullAttributeMapper_2
Note: change case
BulkAttributeRenamer
    ATTRCHOICE = All Attributes
    CASE_CHANGE_TYPE = lower
    MODE_CHOICE = RENAME
    PATTERN_ACTION_DISP = CASECHANGE
    -> BulkAttributeRemover
Note: remove attributes
BulkAttributeRemover
    ATTR_EXP = ^tx_
    -> StringReplacer
Note: StringReplacer / Attributes: location / Mode: Replace Regular Expression / Text To Replace: ^(.+ )([Vv][Aa]\w*)(\s*.*)$ / Replacement Text: \1Vancouver\3
StringReplacer
    CASE = NO
    FIND_TEXT = ^(.+ )([Vv][Aa]\w*)(\s*.*)$
    NO_MATCH = _FME_NO_OP_
    REGEXP = YES
    REPLACE_TEXT = \1Vancouver\3
    SRC_ATTRS = location
    -> AttributeManager
Note: rename & re-order attributes
AttributeManager
    ATTR_TABLE:
      RENAME_SET_VALUE new_account > account
      RENAME_SET_VALUE new_licno > licenceno
      SET_TO _location = @ReplaceRegularExpression(@Value(location),^(.+ )([Vv][Aa]\w*)(\s*.*)$,\1Vancouver\3,caseSensitive=FALSE)
    -> CellTowers (writer OGCGEOPACKAGE_1)
Note: Attribute Definition: Automatic
CellTowers (writer OGCGEOPACKAGE_1)
    attributes: recordid int, account text(20), licenceno text(14), licensee text(34), location text(41), prov text(3), old_account double, old_licno text(11), service text(6), transmit_freq float, receive_freq float, transmit_lower float, transmit_upper float, transmit_bw float, latitude double, longitude double, site_elev double, stuct_ht float, bw_emission text(11), zone_enhancer text(3), last_mod_date datetime, last_upload_date datetime, _location text(200)
Note: deal with <null> TX_PWR
NullAttributeMapper_2
    ATTRCHOICE = Selected Attributes
    ATTRLIST = TX_PWR
    NEW_VALUE = 0
    NULL_TREATMENT = New Value
    SOURCE_ATTR_VAL = Null
    -> Aggregator
Note: Aggregator / Group By: LOCATION / Aggregation Mode: Attributes Only / Accumulation Mode: Use Attributes From One Feature / Generate List: / List Name: _model / Selected Attributes: / TX_ANT_MODEL LICENSEE TX_ANT_MFR / TX_PWR TX_MFR LOCATION RECORDID
Aggregator
    ACCUM_ATTRS_NAME = Use Attributes From One Feature
    GROUP_BY = LOCATION
    LIST_ATTRS_TO_INCLUDE = TX_ANT_MODEL LICENSEE TX_ANT_MFR TX_PWR TX_MFR LOCATION RECORDID
    LIST_NAME = _model
    MODE = Attributes Only
    SEP = ,
    AGGREGATE -> VertexCreator
Note: recover geometry
VertexCreator
    MEASURE_TYPE = Continuous
    MODE_NAME = Replace with Point
    XVAL = @Value(LONGITUDE)
    YVAL = @Value(LATITUDE)
    -> ListHistogrammer
    -> ListSearcher
    -> PythonCaller

Bookmark: Find TX_ANT_MODEL
ListHistogrammer
    LIST_NAME = _histogram
    SRC_LIST = _model{}.TX_ANT_MODEL
    -> ListElementCounter
ListElementCounter
    CNT_ATTR = _modelCount
    LIST_NAME = _histogram{}
    -> TestFilter_2
TestFilter_2
    DEFAULT_VALUE = <UNFILTERED>
    TEST_LIST = "BOOL_OP,OR,COMPOSITE_TEST,""""""1"""""",TEST_CLAUSE,TEST @Value(_modelCount) > 1",>1

Bookmark: unknown antenna models with excess power
Note: PythonCaller: manipulate lists
PythonCaller
    NEW_ATTRIBUTES = _ant_count _ant{}.model
    PYTHONSOURCE:
      import fme
      import fmeobjects
      import re

      # create a list of LOCATIONS where the antenna manufacturer is unknow
      # and the  effective isotropic radiated power (EIRP) >= 50000

      def processFeature(feature):
          # initialize the python lists with FME lists
          _TX_MODEL = feature.getAttribute('_model{}.TX_ANT_MODEL')
          _TX_ANT_MFR = feature.getAttribute('_model{}.TX_ANT_MFR')
          _TX_MFR = feature.getAttribute('_model{}.TX_MFR')
          _TX_PWR = feature.getAttribute('_model{}.TX_PWR')
          _tx_model_unknown = []
          _tx_pwr_unknown = []
          _tx_count = 0

          # test for "MFR" and PWR
          for i in range(len(_TX_PWR)) :
              if  (re.search("ZZ|[0-9].", _TX_MFR[i]) and re.search("ZZ|[0-9].", _TX_ANT_MFR[i]) and float(_TX_PWR[i]) >= 5000.0 ):
                  if (_TX_MODEL[i] not in _tx_model_unknown ) :
                      _tx_model_unknown.append(_TX_MODEL[i])
                  _tx_count = _tx_count + 1

          # output the FME lists
          feature.setAttribute('_ant{}.model', _tx_model_unknown)
          feature.setAttribute('_ant_count', _tx_count)
    PYTHONSYMBOL = processFeature
    -> TestFilter
TestFilter
    DEFAULT_VALUE = <UNFILTERED>
    TEST_LIST = "BOOL_OP,OR,COMPOSITE_TEST,""""""1"""""",TEST_CLAUSE,TEST @Value(_ant_count) > 0",@Value(_tx_count) > 0

Bookmark: ListSearcher in series as an FYI
ListSearcher
    ATTR_VALUE = ZZ|[0-9].
    INDEX_ATTR = _list_index
    LIST_ATTR = _model{}.TX_MFR
    MATCHTYPE = REGULAR_EXPRESSION_ENCODED
    FOUND -> ListSearcher_3
Note: "BAB0021-1744 Galdwin Rd, Abb." is a false positive
ListSearcher_3
    ATTR_VALUE = ZZ|[0-9].
    INDEX_ATTR = _list_index
    LIST_ATTR = _model{}.TX_ANT_MFR
    MATCHTYPE = REGULAR_EXPRESSION_ENCODED
    FOUND -> ListSearcher_2
ListSearcher_2
    ATTR_VALUE = 5000
    INDEX_ATTR = _list_index
    LIST_ATTR = _model{}.TX_PWR
    MATCHTYPE = FIRST_GREATER_THAN_OR_EQUAL_ENCODED
