FME workspace 02.AttributeManipulation - 2020.fmwt
Title: Attribute Manipulation

Parameters:
- SourceDataset_CSV2 = $(FME_MF_DIR)sourceData/DataPoints.csv   # Source CSV (Comma Separated Value) File(s)

Readers:
- CSV2_1: CSV2 from $(SourceDataset_CSV2)

CSV (reader CSV2_1)
    attributes: longitude string, latitude string, elevation string, StationID string, Power string, Quality string, num_measures string, Code string, recorded_tstamp string
    -> StringSearcher
    -> AttributeManager
    -> AttributeSplitter
Note: StringSearcher / String To Search In: @Value(Code) / Regular Expression: ([A-Z]{3})([0-9]+) / Case Sensitive: No / Subexpression Matches List Name: _sub
StringSearcher
    CASE = no
    MATCHED_PARTS_ATTR = _sub
    MATCHED_RESULT_ATTR = _first_match
    REGEXP = ([A-Z]{3})([0-9]+)
    STRING_TO_SEARCH = @Value(Code)
    MATCHED -> StringSearcher_Matched
Note: Results: / Code ABD3627136285 / _first_match ABD3627136285 / _sub{0}.part ABD / _sub{0}.startIndex 0 / _sub{1}.part 3627136285 / _sub{1}.startIndex 3
StringSearcher_Matched: Inspector
Note: AttributeSplitter / Attribute to Split: Code / Delimiter or Format String: 3s10s / List Name: _list
AttributeSplitter
    ATTR_NAME = Code
    DELIMITER = 3s10s
    DROP_EMPTY_PARTS = No
    LIST_NAME = _list
    TRIM_OPTION = Both
    -> AttributeSplitter_Output
Note: Results: / Code ABC1141611430 / _list{0} ABC / _list{1} 1141611430
AttributeSplitter_Output: Inspector
Note: AttributeManager [AttributeManager] / Attribute Actions: / Input Attribute / Output Attribute / Attribute Value / Action / <not set> / alpha / @Left(@Value(Code),3) / Set Value / <not set> / beta / @Substring(@Value(Code),3,-1) / Set Value / <not set> / gamma / @ReplaceRegEx(@Value(Code),([A-Z]{3})([0-9]+),\1) / Set Value
AttributeManager
    ATTR_TABLE:
      SET_TO alpha = @Left(@Value(Code),3)
      SET_TO beta = @Substring(@Value(Code),3,-1)
      SET_TO gamma = @ReplaceRegEx(@Value(Code),([A-Z]{3})([0-9]+),\1)
    -> AttributeManager_Output
Note: Results: / Code ABD3705337067 / alpha ABD / beta 3705337067
AttributeManager_Output: Inspector
