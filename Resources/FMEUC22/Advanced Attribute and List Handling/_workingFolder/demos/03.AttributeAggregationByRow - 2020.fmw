FME workspace 03.AttributeAggregationByRow - 2020.fmw
Title: Previous Attribute

Parameters:
- SourceDataset_CSV2 = \\fs2\Case\C122000\C122718\agg4.txt   # Source CSV (Comma Separated Value) File(s)

Readers:
- CSV2_2: CSV2 from $(SourceDataset_CSV2)

Note: Example Data: / L / N / T / 1 / 105 / 50 / 2 / 102 / 0 / 3 / 90 / 1 / 4 / 100 / 40 / 5 / 100 / 50 / 6 / 30 / 3 / 7 / 35 / 50 / 8 / 40 / 0 / 9 / 40 / 1
CSV (reader CSV2_2)
    attributes: L string, N string, T string
    -> Counter
Note: each row gets a temp ID
Counter
    CNT_ATTR = tmpID
    DOMAIN = counter
    SCOPE = Global
    START = 0
    -> AttributeManager
Note: use conditional to check the T value: / T <= 3 then set the tmpID to the previous rows tmpID i.e. feature[-1].tmpID
AttributeManager
    ATTR_TABLE = SET_TO tmpID = FME_CONDITIONAL:DEFAULT_VALUE'_FME_NO_OP_'BOOL_OP;OR;COMPOSITE_TEST;<Unused>;TEST @Value(T) <= 3'@Value(feature[-1].tmpID)'FME_NUM_CONDITIONS2___
    NUM_PRIOR_FEATURES = 1
    NUM_SUBSEQUENT_FEATURES = 0
    -> Aggregator
Note: use aggregator to sum: / Group By tmpID / (creating the list for validation only)
Aggregator
    ACCUM_ATTRS_NAME = Use Attributes From One Feature
    GROUP_BY = tmpID
    LIST_NAME = _list
    MODE = Attributes Only
    SEP = ,
    SUM = N
    AGGREGATE -> Aggregator_Aggregate
Note: Example Results: / L / N / T / 1 / 297 / 50 / 4 / 100 / 40 / 5 / 130 / 50 / 7 / 115 / 50
Aggregator_Aggregate: Inspector
