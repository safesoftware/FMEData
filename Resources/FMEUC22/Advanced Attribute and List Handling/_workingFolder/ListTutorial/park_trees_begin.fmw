FME workspace park_trees_begin.fmw
Title: Park_Trees

Parameters:
- SourceDataset_CSV2 = $(FME_MF_DIR)sourceData\street-trees.csv   # Source CSV (Comma Separated Value) File(s)
- SourceDataset_GEOJSON = $(FME_MF_DIR)sourceData\parks-polygon-representation.geojson   # Source GeoJSON File or URL

Readers:
- CSV2_1: CSV2 from $(SourceDataset_CSV2)
- GEOJSON_1: GEOJSON from $(SourceDataset_GEOJSON)

Note: City of Vancouver - Open Data Portal : / Street Trees
CSV (reader CSV2_1)
    attributes: TREE_ID uint32, CIVIC_NUMBER uint32, STD_STREET varchar(21), GENUS_NAME varchar(15), SPECIES_NAME varchar(19), CULTIVAR_NAME varchar(21), COMMON_NAME varchar(31), ASSIGNED varchar(2), ROOT_BARRIER varchar(2), PLANT_AREA varchar(3), ON_STREET_BLOCK uint32, ON_STREET varchar(21), NEIGHBOURHOOD_NAME varchar(25), STREET_SIDE_NAME varchar(5), HEIGHT_RANGE_ID uint32, DIAMETER real32, CURB varchar(2), DATE_PLANTED date, Geom varchar(59)
    -> GeometryReplacer
Note: Interpret the GeoJSON geometry field
GeometryReplacer
    KIND_LONG = GeoJSON
    REMOVE_ATTRIBUTE = Yes
    SOURCE = @Value(Geom)
    -> CoordinateSystemSetter
CoordinateSystemSetter
    COORDSYS = LL-WGS84
    -> AttributeValueMapper
Note: Map HEIGHT_RANGE_ID: / 0-10 for every 10 feet / (e.g., 0 = 0-10 ft, 1 = 10-20 ft, 2 = 20-30 ft, and10 = 100+ ft)
AttributeValueMapper
    LUT = 0,0-10,1,10-20,2,20-30,3,30-40,4,40-50,5,50-60,6,60-70,7,70-80,8,80-90,9,90-100,10,100-110,11,110-120
    MAPPING_DIRECTION = FORWARD
    SRC = HEIGHT_RANGE_ID
    VAL_ATTR = HEIGHT_RANGE
    -> PointOnAreaOverlayer [POINT]
Note: City of Vancouver - Open Data Portal : / Park Polygons
parks-polygon-representation (reader GEOJSON_1)
    attributes: park_name string, park_id float, area_ha float, park_url string
    -> PointOnAreaOverlayer [AREA]
Note: Overlay the trees and the parks to see which parks contain trees.
PointOnAreaOverlayer
    DEAGGREGATE_INPUT = Yes
    OV_ATTR = _overlaps
    POLYS_FIRST = NO
