FME workspace park_trees_start.fmw
Title: Park_Trees

Parameters:
- SourceDataset_MITAB = $(FME_MF_DIR)park_trees_start/1/Parks/Parks.tab   # Source MapInfo TAB (MITAB) File(s)
- SourceDataset_FILEGDB = $(FME_MF_DIR)park_trees_start/1/Addresses/Addresses.gdb   # File Geodatabase

Readers:
- MITAB_1: MITAB from $(SourceDataset_MITAB)
- FILEGDB_1: FILEGDB from $(SourceDataset_FILEGDB)

Parks (reader MITAB_1)
    attributes: ParkId smallint, RefParkId smallint, ParkName char(40), NeighborhoodName char(40), EWStreet char(30), NSStreet char(30), DogPark char(1), Washrooms char(1), SpecialFeatures char(1)
    -> PointOnAreaOverlayer [AREA]
    -> 2_Parks
Note: Overlay the trees and the parks to see which parks contain trees.
PointOnAreaOverlayer
    DEAGGREGATE_INPUT = Yes
    OV_ATTR = _overlaps
    POLYS_FIRST = NO
    POINT -> Result
Result: Inspector [off]

Bookmark: Use Address table to add spatial information to the public trees CSV file
Note: Read PostalAddress. / Also, remove some irrelevant attributes / to clean up our workspace and save / memory.
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> DatabaseJoiner
Note: Tree data location: / Join the tree data with the address data based on a shared address field. Now our point features will contain information about tree species.
DatabaseJoiner
    ADDED_FIELDS = CommonName Cultivar Diameter Genus Height PlantingDate Species TreeID
    ATTR_ACCUM_MODE = Merge Joined
    ATTR_CONFLICT_RES = Use Original
    CSV2_CASE_SENSITIVE_FIELD_NAMES = Yes
    CSV2_DATA_START_LINE = 2
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(FME_MF_DIR)park_trees_start/1/Parks/PublicTrees.csv
    FORMAT = CSV2
    JOIN_KEYS = PSTLADDRESS Address
    MATCH_MULTIPLE_DISPLAY = Create a feature for each match
    MATCH_RULE_DISPLAY = Match All (1:M)
    TABLE = CSV
    JOINED -> 1_Points
    JOINED -> PointOnAreaOverlayer [POINT]

Bookmark: Initial Data Inspection
1_Points: Inspector
2_Parks: Inspector
