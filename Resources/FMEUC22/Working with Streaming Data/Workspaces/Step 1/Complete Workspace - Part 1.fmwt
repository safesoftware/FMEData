FME workspace Complete Workspace - Part 1.fmwt
Title: KAFKA to POSTGIS

Parameters:
- kafka_username =   # Kafka User Name
- kafka_pw =   # Kafka Password
- kafka_topic = cov-fleet-location
- DestDataset_POSTGIS = FME Training Postgres DB   # Connection

Writers:
- POSTGIS_1: POSTGIS to $(DestDataset_POSTGIS)

Note: Parse out attributes
JSONFlattener
    ERROR_LIST_ATTR = _json_error
    JSON_DOCUMENT = @Value(_value)
    NEW_ATTRIBUTES = vehicle_id timestamp vehicle_category vehicle_type geo
    READ_FROM_FILE = NO
    RECURSIVE = Yes
    -> Tester
Note: Filter just trucks
Tester
    BOOL_OP = OR
    TEST_CLAUSE = TEST @Value(vehicle_type) = trucks
    TEST_MODE = TEST
    PASSED -> GeometryReplacer
Note: Remove and reorder attributes
AttributeManager
    -> TruckFleetStream (writer POSTGIS_1)
Note: Write to PostGIS
TruckFleetStream (writer POSTGIS_1)
    attributes: _creation_instance numeric(20,0), _value varchar(200), _timestamp varchar(200), _topic varchar(200), _connector_id varchar(200), vehicle_id text, timestamp text, vehicle_category text, vehicle_type text

Bookmark: Connect to fleet tracking Kafka queue
Creator
    GEOMTYPE = Geometry Object
    NUM = 1
    CREATED -> KafkaConnector
KafkaConnector
    __kafka_action_multiparam = __kafka_topics_list]$(kafka_topic)]__kafka_receive_mode]batch]__kafka_max_messages]<Unused>]__kafka_batch_size]1000]__kafka_consumer_group_id]simulate-geofence]__kafka_starting_offset]earliest]__kafka_partition]<Unused>]__kafka_custom_offset]<Unused>]__kafka_auto_commit]YES]__kafka_advanced_options_group]FME_DISCLOSURE_CLOSED]__kafka_advanced_options]]__kafka_message_options_group]FME_DISCLOSURE_OPEN]__kafka_message_schema]simple]__kafka_value_encoding]utf-8]__kafka_schema_registry]<Unused>]__kafka_attributes_to_add]"_value _timestamp _topic"]FME_CONTROLLER_QUERY_FILE]kafka_deps/Receive.fme]FME_CONTROLLER_CHOICE]Receive
    __kafka_brokers_list = pkc-4nym6.us-east-1.aws.confluent.cloud:9092
    __kafka_credential_source = embedded
    __kafka_operation_type = Receive
    __kafka_password = $(kafka_pw)
    __kafka_sasl_mechanisms = PLAIN
    __kafka_security_protocol = SASL_SSL
    __kafka_username = $(kafka_username)
    -> JSONFlattener

Bookmark: Build point geometries
Note: Create points from WKT
GeometryReplacer
    KIND_LONG = OGC Well Known Text
    OGC_WKT_PRECISION_DISPLAY = 64-bit
    REMOVE_ATTRIBUTE = Yes
    SOURCE = @Value(geo)
    -> CoordinateSystemSetter
CoordinateSystemSetter
    COORDSYS = LL84
    -> AttributeManager
