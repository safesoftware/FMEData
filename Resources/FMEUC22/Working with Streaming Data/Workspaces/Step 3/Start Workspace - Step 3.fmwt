FME workspace Start Workspace - Step 3.fmwt
Title: SHAPEFILE to GEOJSON

Parameters:
- SourceDataset_FILEGDB = /private/var/folders/lh/rr_tj9hj32d60wl0tzzl71q00000gp/T/wb_template_1659976843275_4145/1/Part 3/dgtl_road_atlas.gdb   # File Geodatabase
- kafka_username =   # User Name
- kafka_password =   # Password

Readers:
- FILEGDB_1: FILEGDB from $(SourceDataset_FILEGDB)

Note: The stream tracks 50,000 vehicles over rush hour in the lower mainland. Rather than storing the location of the vehicle every five seconds we only need accuracy at 30 second interval.

Bookmark: Connect to Kafka
Creator
    GEOMTYPE = Geometry Object
    NUM = 1
    CREATED -> KafkaConnector
KafkaConnector
    __kafka_action_multiparam = __kafka_topics_list]moving-assets-rush-hour]__kafka_receive_mode]stream]__kafka_max_messages]]__kafka_batch_size]<Unused>]__kafka_consumer_group_id]simulate-geofence]__kafka_starting_offset]earliest]__kafka_partition]<Unused>]__kafka_custom_offset]<Unused>]__kafka_auto_commit]YES]__kafka_advanced_options_group]FME_DISCLOSURE_CLOSED]__kafka_advanced_options]]__kafka_message_options_group]FME_DISCLOSURE_OPEN]__kafka_message_schema]simple]__kafka_value_encoding]utf-8]__kafka_schema_registry]<Unused>]__kafka_attributes_to_add]"_value _timestamp _topic"]FME_CONTROLLER_QUERY_FILE]kafka_deps/Receive.fme]FME_CONTROLLER_CHOICE]Receive
    __kafka_brokers_list = pkc-4nym6.us-east-1.aws.confluent.cloud:9092
    __kafka_credential_source = embedded
    __kafka_operation_type = Receive
    __kafka_password = $(kafka_password)
    __kafka_sasl_mechanisms = PLAIN
    __kafka_security_protocol = SASL_SSL
    __kafka_username = $(kafka_username)
    -> JSONFlattener
JSONFlattener
    ERROR_LIST_ATTR = _json_error
    JSON_DOCUMENT = @Value(_value)
    NEW_ATTRIBUTES = path_id path_segment_id geometry start_time timestamp
    READ_FROM_FILE = NO
    RECURSIVE = Yes

Bookmark: Read the road data in for the Lower Mainland
Note: WHERE Clause on the reader restricts to features within City of Vancouver. Download the Geodatabase dataset here.
GBA/TRANSPORT_LINE (reader FILEGDB_1)
    attributes: OBJECTID objectid, TRANSPORT_LINE_ID int, CREATE_INTEGRATION_SESSION_ID int, CREATE_INTEGRATION_DATE date, MODIFY_INTEGRATION_SESSION_ID int, MODIFY_INTEGRATION_DATE date, CREATE_PARTNER_ORG_ID int, CREATE_PARTNER_ORG text(110), MODIFY_PARTNER_ORG_ID int, MODIFY_PARTNER_ORG text(110), CUSTODIAN_PARTNER_ORG_ID int, CUSTODIAN_PARTNER_ORG text(110), DATA_CAPTURE_METHOD_CODE text(30), Z_VALUE_DERIVED_IND text(1), CAPTURE_DATE date, DEACTIVATION_DATE date, TRANSPORT_LINE_TYPE_CODE text(3), TRANSPORT_LINE_SURFACE_CODE text(1), TRANSPORT_LINE_DIVIDED_CODE text(1), TRAVEL_DIRECTION_CODE text(1), TRANSPORT_LINE_STRUCTURE_CODE text(1), SPEED_LIMIT smallint, LEFT_NUMBER_OF_LANES smallint, RIGHT_NUMBER_OF_LANES smallint, TOTAL_NUMBER_OF_LANES smallint, UNDER_CONSTRUCTION_IND text(1), VIRTUAL_IND text(1), DISASTER_ROUTE_IND text(1), TRUCK_ROUTE_IND text(1), LEFT_LOCALITY_ID int,
      LEFT_LOCALITY text(50), RIGHT_LOCALITY_ID int, RIGHT_LOCALITY text(50), LEFT_REGIONAL_DISTRICT_ID text(5), RIGHT_REGIONAL_DISTRICT_ID text(5), STRUCTURED_NAME_1_ID int, STRUCTURED_NAME_1 text(100), STRUCTURED_NAME_2_ID int, STRUCTURED_NAME_2 text(100), STRUCTURED_NAME_3_ID int, STRUCTURED_NAME_3 text(100), STRUCTURED_NAME_4_ID int, STRUCTURED_NAME_4 text(100), STRUCTURED_NAME_5_ID int, STRUCTURED_NAME_5 text(100), STRUCTURED_NAME_6_ID int, STRUCTURED_NAME_6 text(100), STRUCTURED_NAME_7_ID int, STRUCTURED_NAME_7 text(100), HIGHWAY_ROUTE_1 text(5), HIGHWAY_ROUTE_2 text(5), HIGHWAY_ROUTE_3 text(5), HIGHWAY_EXIT_NUMBER text(5), INDUSTRY_NAME_1 text(255), INDUSTRY_NAME_2 text(255), INDUSTRY_NAME_3 text(255), SINGLE_HOUSE_NUMBER int, LEFT_HOUSE_NUM_SCHEME_CODE text(1), FROM_LEFT_HOUSE_NUMBER int, TO_LEFT_HOUSE_NUMBER int,
      RIGHT_HOUSE_NUM_SCHEME_CODE text(1), FROM_RIGHT_HOUSE_NUMBER int, TO_RIGHT_HOUSE_NUMBER int, LANE_RESTRICTION_CODE text(1), ACCESS_RESTRICTION_CODE text(2), FROM_TRAFFIC_IMPACTOR_CODE text(1), TO_TRAFFIC_IMPACTOR_CODE text(1), FROM_LEFT_TURN_TIME_CODE text(8), FROM_CENTRE_TURN_TIME_CODE text(8), FROM_RIGHT_TURN_TIME_CODE text(8), TO_LEFT_TURN_TIME_CODE text(8), TO_CENTRE_TURN_TIME_CODE text(8), TO_RIGHT_TURN_TIME_CODE text(8), FROM_VEHICLE_MAX_WEIGHT_KG int, TO_VEHICLE_MAX_WEIGHT_KG int, FROM_VEHICLE_MAX_WIDTH_METRE double, TO_VEHICLE_MAX_WIDTH_METRE double, FROM_VEHICLE_MAX_HEIGHT_METRE double, TO_VEHICLE_MAX_HEIGHT_METRE double, MINISTRY_OF_TRANSPORT_ID int, MINISTRY_OF_TRANSPORT_NAME text(255), INTEGRATION_NOTES text(4000), EXCLUDED_RULES text(4000), DEMOGRAPHIC_IND text(1), FROM_TRANSPORT_NODE_POINT_ID int, TO_TRANSPORT_NODE_POINT_ID int
    -> Tester
Note: Only major routes.
Tester
    BOOL_OP = OR
    TEST_CLAUSE = TEST @Value(TRANSPORT_LINE_TYPE_CODE) IN RA1,RA2,RC1,RC2,RF,RH1,RH2
    TEST_MODE = TEST
    PASSED -> AttributeKeeper
AttributeKeeper
    CREATE_BULK_MODE_FEATURES = NO
    KEEP_ATTRS = OBJECTID,TRANSPORT_LINE_TYPE_CODE,LEFT_NUMBER_OF_LANES,RIGHT_NUMBER_OF_LANES,SPEED_LIMIT,TOTAL_NUMBER_OF_LANES,DISASTER_ROUTE_IND,LEFT_LOCALITY,RIGHT_LOCALITY,STRUCTURED_NAME_1
    -> CoordinateSystemSetter
CoordinateSystemSetter
    COORDSYS = NAD83.BC/Albers
