FME workspace Start Workspace - Part 1.fmw
Title: KAFKA to POSTGIS

Parameters:
- kafka_broker_name =   # Kafka Host Name
- kafka_username =   # Kafka User Name
- kafka_pw =   # Kafka Password
- kafka_topic = cov-fleet-location
- kafka_consumer_group_id = enter-your-name   # Consumer Group ID

Bookmark: Connect to fleet tracking Kafka queue
Creator
    GEOMTYPE = Geometry Object
    NUM = 1
    CREATED -> KafkaConnector
KafkaConnector
    __kafka_action_multiparam = __kafka_topics_list]$(kafka_topic)]__kafka_receive_mode]batch]__kafka_max_messages]<Unused>]__kafka_batch_size]1000]__kafka_consumer_group_id]$(kafka_consumer_group_id)]__kafka_starting_offset]earliest]__kafka_partition]<Unused>]__kafka_custom_offset]<Unused>]__kafka_auto_commit]YES]__kafka_advanced_options_group]FME_DISCLOSURE_CLOSED]__kafka_advanced_options]]__kafka_message_options_group]FME_DISCLOSURE_OPEN]__kafka_message_schema]simple]__kafka_value_encoding]utf-8]__kafka_schema_registry]<Unused>]__kafka_attributes_to_add]"_value _timestamp _topic"]FME_CONTROLLER_QUERY_FILE]kafka_deps/Receive.fme]FME_CONTROLLER_CHOICE]Receive
    __kafka_brokers_list = $(kafka_broker_name):9092
    __kafka_credential_source = embedded
    __kafka_operation_type = Receive
    __kafka_password = $(kafka_pw)
    __kafka_sasl_mechanisms = PLAIN
    __kafka_security_protocol = SASL_SSL
    __kafka_username = $(kafka_username)
