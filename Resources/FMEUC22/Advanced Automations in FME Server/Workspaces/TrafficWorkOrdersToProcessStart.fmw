FME workspace TrafficWorkOrdersToProcessStart.fmw
Title: CSV2 to AUTOMATIONS

Parameters:
- SourceDataset_CSV2 = c:\FMEData\Resources\FMEUC22\Advanced Automations in FME Server\Data\TrafficWorkOrders.csv   # Source CSV (Comma Separated Value) File(s)

Readers:
- CSV2_2: CSV2 from $(SourceDataset_CSV2)

Writers:
- AUTOMATIONS_2: AUTOMATIONS to <Unused>

Note: Read Workorders database
CSV (reader CSV2_2)
    attributes: Work Order ID varchar(13), Status varchar(12), Asset Type varchar(36), Asset ID uint32, Location ID varchar(13), Created Date varchar(29), Modified Date varchar(29), Submitted Date varchar(29), Closed Date varchar(29), Fiscal Year uint32, Work Type varchar(15), Work Needed varchar(223), Work Type Other varchar(464), Work Requested By varchar(35), Job Description varchar(1032), Problem Found varchar(598), Action Taken varchar(2526), Follow-Up Needed varchar(6), Child Work Order varchar(13), Parent Work Order varchar(13), Is Follow-Up varchar(6), TMC Issue ID varchar(13), Service Request # varchar(13), Damage Report varchar(85), Location Name varchar(80), Latitude varchar(1), Longitude varchar(1), Location varchar(46)
    -> Tester
Note: Fetch school workorders that have not been processed
Tester
    BOOL_OP = COMPOSITE
    COMPOSITE_TEST = 1 AND ( 2 OR 3 )
    TEST_CLAUSE:
      TEST @Value(Status) = Submitted
      TEST @Value(Asset Type) = School Beacon Zone
      TEST @Value(Asset Type) = School Beacon
    TEST_MODE = TEST
    PASSED -> AttributeKeeper
Note: Clean up attributes to keep only those needed for processing
AttributeKeeper
    CREATE_BULK_MODE_FEATURES = NO
    KEEP_ATTRS = Asset ID,Asset Type,Service Request #,Work Needed,Work Order ID,Work Type,Location,Job Description,Problem Found
    -> WorkOrders (writer AUTOMATIONS_2)
Note: Send to Automation Writer for downstream processing
WorkOrders (writer AUTOMATIONS_2)
    attributes: Work Order ID string, Asset Type string, Asset ID int, Work Type string, Work Needed string, Job Description string, Problem Found string, Service Request # string, Location string
