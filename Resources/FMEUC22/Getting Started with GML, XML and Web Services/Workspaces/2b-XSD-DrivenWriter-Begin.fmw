FME workspace 2b-XSD-DrivenWriter-Begin.fmw
Title: How to Consume and Produce XML Using Application Schemas with the XSD Driven Writer

Creator
    GEOM = <?xml version="1.0" encoding="US_ASCII" standalone="no" ?><geometry><polygon><line><coord x="0" y="0"/><coord x="1" y="0"/><coord x="1" y="1"/><coord x="0" y="1"/><coord x="0" y="0"/></line></polygon></geometry>
    GEOMTYPE = Geometry Object
    NUM = 1
    CREATED -> AttributeCreator
AttributeCreator
    ATTR_TABLE:
      SET_TO language = en-US
      SET_TO category{0} = Safety
      SET_TO responseType{0} = Monitor
      SET_TO event = Flood
      SET_TO urgency = Expected
      SET_TO severity = Moderate
      SET_TO description = Test Message:
        Monitor flood levels on the Fraser River near Fort Langley.
      SET_TO certanity = Observed
      SET_TO contact = lizard@safe.com
