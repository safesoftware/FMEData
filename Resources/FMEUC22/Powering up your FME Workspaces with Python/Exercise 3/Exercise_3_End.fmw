FME workspace Exercise_3_End.fmw

Parameters:
- SourceDataset_CSV2 = .\CellSignal.csv   # Source CSV (Comma Separated Value) File(s)

Readers:
- CSV2_1: CSV2 from $(SourceDataset_CSV2)

CSV (reader CSV2_1)
    attributes: longitude x_coordinate, latitude y_coordinate, StationID uint16, Power real64, Quality real32, num_measures uint16, Code string, recorded_tstamp string
    -> Sampler
Sampler
    RATE = 10
    SAMPLE_MODE = No
    SAMPLE_TYPE_LONG = First N Features
    SAMPLED -> PythonCaller
    SAMPLED -> PythonCaller_2
    SAMPLED -> PythonCaller_3
Note: Calculate statistics
PythonCaller
    HIDE_ATTRIBUTES = Code latitude longitude num_measures Power Quality recorded_tstamp StationID
    NEW_ATTRIBUTES = min max sum avg
    PYTHONSOURCE:
      import fme
      import fmeobjects


      # Template Class Interface:
      # When using this class, make sure its name is set as the value of
      # the 'Class or Function to Process Features' transformer parameter
      class FeatureProcessor(object):
          def __init__(self):
              self.qualities = []

          def input(self,feature):
              self.qualities.append(feature.getAttribute('Quality'))

          def close(self):
              maximum = max(self.qualities)
              minimum = min(self.qualities)
              summe = sum(self.qualities)
              avg = summe/len(self.qualities)

              feature = fmeobjects.FMEFeature()
              feature.setAttribute('max', maximum)
              feature.setAttribute('min', minimum)
              feature.setAttribute('sum', summe)
              feature.setAttribute('avg', avg)

              self.pyoutput(feature)
    PYTHONSYMBOL = FeatureProcessor
Note: Custom group by implementation
PythonCaller_2
    HIDE_ATTRIBUTES = Code latitude longitude num_measures Power Quality recorded_tstamp StationID
    NEW_ATTRIBUTES = min max sum avg station
    PYTHONSOURCE:
      import fme
      import fmeobjects


      # Template Class Interface:
      # When using this class, make sure its name is set as the value of
      # the 'Class or Function to Process Features' transformer parameter
      class FeatureProcessor(object):
          def __init__(self):
              self.stations = {}


          def input(self,feature):
              station = feature.getAttribute('StationID')
              if station not in self.stations:
                  self.stations[station] = []
              self.stations[station].append(feature.getAttribute('Quality'))

          def close(self):
              for station in self.stations:
                  qualities = self.stations[station]
                  maximum = max(qualities)
                  minimum = min(qualities)
                  summe = sum(qualities)
                  avg = summe/len(qualities)

                  feature = fmeobjects.FMEFeature()
                  feature.setAttribute('max', maximum)
                  feature.setAttribute('min', minimum)
                  feature.setAttribute('sum', summe)
                  feature.setAttribute('avg', avg)
                  feature.setAttribute('station', station)

                  self.pyoutput(feature)
    PYTHONSYMBOL = FeatureProcessor
Note: FME Group by (2021)
PythonCaller_3
    GROUP_BY = StationID
    HIDE_ATTRIBUTES = Code latitude longitude num_measures Power Quality recorded_tstamp StationID
    NEW_ATTRIBUTES = min max sum avg station
    PYTHONSOURCE:
      import fme
      import fmeobjects


      class FeatureProcessor(object):
          """Template Class Interface:
          When using this class, make sure its name is set as the value of the 'Class
          to Process Features' transformer parameter.
          """

          def __init__(self):
              """Base constructor for class members."""
              self.stations = []

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.stations.append(feature)


          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              qualities = []
              for station in self.stations:
                  qualities.append(float(station.getAttribute('Quality')))

              maximum = max(qualities)
              minimum = min(qualities)
              summe = sum(qualities)
              avg = summe/len(qualities)

              feature = fmeobjects.FMEFeature()
              feature.setAttribute('max', maximum)
              feature.setAttribute('min', minimum)
              feature.setAttribute('sum', summe)
              feature.setAttribute('avg', avg)
              feature.setAttribute('station', self.stations[0].getAttribute('StationID'))

              self.stations = []

              self.pyoutput(feature)
    PYTHONSYMBOL = FeatureProcessor
