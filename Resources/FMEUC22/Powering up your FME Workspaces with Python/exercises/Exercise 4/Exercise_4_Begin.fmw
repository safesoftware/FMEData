FME workspace Exercise_4_Begin.fmw

Parameters:
- SourceDataset_FFS = .\waterlevel_list.ffs   # Source FME Feature Store (FFS) File(s)

Readers:
- FFS_1: FFS from $(SourceDataset_FFS)

waterlevel (reader FFS_1)
    attributes: level_number number(11,0), km number(8,3), name varchar(31), measurements{}.measurement number(8,2)
    -> PythonCaller
ListElementCounter
    CNT_ATTR = _element_count
    LIST_NAME = measurements{}
    -> ListSummer
ListSummer
    RESULT = _sum
    SRC_LIST = measurements{}.measurement
    -> ExpressionEvaluator
ExpressionEvaluator
    ACTION = Create New Attribute
    EXPRESSION = @Value(_sum)/@Value(_element_count)
    VAL_ATTR = messwerte_mean

Bookmark: Edit Python Template
PythonCaller
    PYTHONSOURCE:
      import fme
      import fmeobjects


      class FeatureProcessor(object):
          def __init__(self):
              pass

          def input(self, feature):
              # Add your code here

              self.pyoutput(feature)

          def close(self):
              pass

          def process_group(self):
              pass
    PYTHONSYMBOL = FeatureProcessor
    -> ListElementCounter
