FME workspace extracting-location-from-json.fmw
Title: Extracting Locations from JSON

Parameters:
- SourceDataset_JSON_3 = https://opendata.vancouver.ca/explore/dataset/rental-standards-current-issues/download/?format=json   # Source JSON (JavaScript Object Notation) File or URL
- DestDataset_OGCKML = c:\FMEData\Resources\FMEUC22\GettingStartedWithJSON\2_ExtractingLocationsFromJSON\Output\RentalStandardsIssues.kml.kml   # Destination Google KML File

Readers:
- JSON_2: JSON from $(SourceDataset_JSON_3)

Writers:
- OGCKML_1: OGCKML to $(DestDataset_OGCKML)

Bookmark: Reader Feature Types
JSONFeature (reader JSON_2)
    attributes: datasetid string, recordid string, fields.businessoperator string, fields.geo_local_area string, fields.totalunits int, fields.streetnumber string, fields.detailurl string, fields.street string, fields.geom.coordinates{} float, fields.geom.type string, fields.totaloutstanding int, record_timestamp string
    -> AttributeCreator

Bookmark: Create points
AttributeCreator
    ATTR_TABLE:
      SET_TO longitude = @Value(fields.geom.coordinates{0})
      SET_TO latitude = @Value(fields.geom.coordinates{1})
      SET_TO issuepercentage = @Evaluate(@Value(fields.totaloutstanding)/@Value(fields.totalunits)*100)
    -> VertexCreator
VertexCreator
    CLOSE_LINES = Yes
    IGNORE_DUPLICATES = Yes
    MEASURE_TYPE = Continuous
    MISSING_VAL_MODE = Compute
    MODE_NAME = Add Point
    XVAL = @Value(longitude)
    YVAL = @Value(latitude)
    -> CoordinateSystemSetter
    <REJECTED> -> Logger
CoordinateSystemSetter
    COORDSYS = LL84
    -> KMLPropertySetter
Logger
    LOG_FEATURE = LOG_ONLY
    MAXCOORDS = 20
    MAXFEATS = 20
    MESSAGE = Feature is:
    SEVERITY = INFO

Bookmark: Style KML
KMLPropertySetter
    ADD_ATTR_TABLE = Yes
    ATTR_TABLE_TITLE = Attributes
    CONTENT_TYPE = Text
    EXTRUDE = No
    GEOM_TYPE = Vector
    NAME = @Value(fields.totalunits)
    SUMMARY = <none>
    TESSELATE = Yes
    VISIBILITY = Yes
    -> KMLStyler
KMLStyler
    FILL_OPACITY = 0.4
    ICON_NAME = FME_CONDITIONAL:DEFAULT_VALUE'H1'BOOL_OP;OR;COMPOSITE_TEST;1;TEST @Value(issuepercentage) <= 5'C1'BOOL_OP;OR;COMPOSITE_TEST;1;TEST @Value(issuepercentage) <= 10'E2'FME_NUM_CONDITIONS3___
    ICON_OPACITY = 1.0
    ICON_SCALE = .5
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> RentalStandardIssues (writer OGCKML_1)

Bookmark: Writer Feature Types
RentalStandardIssues (writer OGCKML_1)
    attributes: longitude kml_char(200), latitude kml_char(200), issuepercentage kml_char(200), datasetid kml_char(255), recordid kml_char(255), fields.businessoperator kml_char(255), fields.geo_local_area kml_char(255), fields.totalunits kml_char(20), fields.streetnumber kml_char(255), fields.detailurl kml_char(255), fields.street kml_char(255), fields.geom.coordinates{} kml_real64, fields.geom.type kml_char(255), fields.totaloutstanding kml_char(20), record_timestamp kml_char(255)
