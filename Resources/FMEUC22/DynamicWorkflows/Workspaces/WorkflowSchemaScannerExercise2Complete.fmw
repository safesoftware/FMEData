FME workspace WorkflowSchemaScannerExercise2Complete.fmw

Parameters:
- SourceDataset_CSV2 = ""C:\FMEData2022\Resources\FMEUC22\DynamicWorkflows\Data\Cedar Cottage.csv" "C:\FMEData2022\Resources\FMEUC22\DynamicWorkflows\Data\Vancouver Farmers Markets.csv""   # Source CSV (Comma Separated Value) File(s)
- FEATURE_TYPES =
- DestDataset_CSV2 = C:\FMEData2022\Resources\FMEUC22\DynamicWorkflows\Output   # Destination CSV (Comma Separated Value) Folder

Readers:
- CSV2_1: CSV2 from $(SourceDataset_CSV2)

Writers:
- CSV2_2: CSV2 to $(DestDataset_CSV2)

AttributeManager
    ATTR_TABLE:
      SET_TO Hours = @Value(Open) - @Value(Close)
      REMOVE Open
      REMOVE Close
    -> SchemaScanner
SchemaScanner
    CASE = No
    EMPTY_ATTR_HANDLING = INFER_EMPTY_SCHEMA
    GROUP_BY = Day
    HOLD = Yes
    IGNORE_REGEXP = fme_|csv_|multi_
    SCHEMA_NAME_ATTR = fme_feature_type_name
    UNBOUNDED_NUMBERS = Yes
    UNBOUNDED_STRINGS = No
    -> DYNAMIC (writer CSV2_2)
    <SCHEMA> -> DYNAMIC (writer CSV2_2)

Bookmark: Reader Feature Types
CSV (reader CSV2_1)
    attributes: MarketType varchar(22), MarketName varchar(49), MergedAddress varchar(34), Day varchar(30), Open varchar(18), Close varchar(18), Months varchar(13), NumberOfVendors varchar(11)
    -> AttributeManager

Bookmark: Writer Feature Types
DYNAMIC (writer CSV2_2)
