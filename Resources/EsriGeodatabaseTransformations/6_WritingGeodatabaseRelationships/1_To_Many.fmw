FME workspace 1_To_Many.fmw
Title: 1 to Many

Parameters:
- SourceDataset_GEODATABASE_FILE = $(FME_MF_DIR)1ManyRelationshipStart.gdb   # File Geodatabase
- DestDataset_GEODATABASE_FILE = $(FME_MF_DIR)Output\1_to_many.gdb   # File Geodatabase

Readers:
- GEODATABASE_FILE_3: GEODATABASE_FILE from $(SourceDataset_GEODATABASE_FILE)

Writers:
- GEODATABASE_FILE_1: GEODATABASE_FILE to $(DestDataset_GEODATABASE_FILE)

A_A_Parcels (reader GEODATABASE_FILE_3)
    attributes: OBJECTID integer, PARCELID integer, GFID guid, Shape_Length double, Shape_Area double, NeighbourID integer
    -> AttributeCreator
AttributeCreator
    ATTR_TABLE:
      SET_TO geodb_feature_has_relationships = yes
      SET_TO geodb_oid = @Value(OBJECTID)
    -> A_A_Parcels (writer GEODATABASE_FILE_1)
A_A_Parcels (writer GEODATABASE_FILE_1)
    attributes: OBJECTID integer, PARCELID integer, GFID char(2048), NeighbourID integer, Shape_Length double, Shape_Area double
A_Neighborhoods (reader GEODATABASE_FILE_3)
    attributes: OBJECTID integer, ID double, NAME char(20), URL char(60), POP2001 double, POP2011 double, GFID guid, SHAPE_Length double, SHAPE_Area double
    -> AttributeCreator_2
AttributeCreator_2
    ATTR_TABLE:
      SET_TO geodb_feature_has_relationships = yes
      SET_TO geodb_oid = @Value(OBJECTID)
    -> A_Neighborhoods (writer GEODATABASE_FILE_1)
A_Neighborhoods (writer GEODATABASE_FILE_1)
    attributes: OBJECTID integer, ID double, NAME char(20), URL char(60), POP2001 double, POP2011 double, GFID char(2048), SHAPE_Length double, SHAPE_Area double
