FME workspace PointOnLineOverlayer.fmw

Parameters:
- SourceDataset_GEODATABASE_FILE = ..\Simple\SchemaMappingExercise\TrainingWater.gdb   # File Geodatabase

Readers:
- GEODATABASE_FILE_1: GEODATABASE_FILE from $(SourceDataset_GEODATABASE_FILE)

waterFittings (reader GEODATABASE_FILE_1)
    attributes: OBJECTID integer, FACILITYID char(20), INSTALLDATE date, FITTINGTYPE char(50), LOCDESC char(200), ROTATION double, ENABLED smallint, ACTIVEFLAG smallint, OWNEDBY smallint, MAINTBY smallint, LASTUPDATE date, LASTEDITOR char(50), GlobalID char(38)
    -> PointOnLineOverlayer [POINT]
waterLaterals (reader GEODATABASE_FILE_1)
    attributes: OBJECTID integer, FACILITYID char(20), INSTALLDATE date, MATERIAL char(20), LINETYPE char(30), LOCDESC char(50), DIAMETER double, WATERTYPE char(30), ENABLED smallint, ACTIVEFLAG smallint, OWNEDBY smallint, MAINTBY smallint, LASTUPDATE date, LASTEDITOR char(50), GlobalID char(38), SHAPE_Length double
    -> PointOnLineOverlayer [LINE]
waterMains (reader GEODATABASE_FILE_1)
    attributes: OBJECTID integer, FACILITYID char(20), INSTALLDATE date, MATERIAL char(20), DIAMETER double, WATERTYPE char(30), TRANSMISS char(5), ENABLED smallint, ACTIVEFLAG smallint, OWNEDBY smallint, MAINTBY smallint, LASTUPDATE date, LASTEDITOR char(50), GlobalID char(38), Shape_Length double
    -> PointOnLineOverlayer [LINE]
PointOnLineOverlayer
    CANDIDATE_LIST_ATTRS_TO_INCLUDE = FITTINGTYPE GlobalID fme_feature_type
    CANDIDATE_LIST_ATTRS_TO_INCLUDE_MODE = Selected Attributes
    CANDIDATE_LIST_NAME = _JunctionsConnected
    DEAGGREGATE_INPUT = Yes
    LIST_ATTRS_TO_INCLUDE = DIAMETER LINETYPE MATERIAL TRANSMISS fme_feature_type
    LIST_NAME = _pipes
    OV_ATTR = _overlaps
    TOLERANCE = 0.1
    POINT -> PointOnLineOverlayer_Point
    LINE -> PointOnLineOverlayer_Line
PointOnLineOverlayer_Point: Inspector
PointOnLineOverlayer_Line: Inspector
