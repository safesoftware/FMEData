FME workspace webapp.kml.fmw

Parameters:
- SourceDataset_ACAD = $(FME_MF_DIR)Data\bad_data.dwg   # Source Autodesk AutoCAD DWG/DXF File(s)
- DestDataset_OGCKML = /Users/semery/Desktop/WebApp Stuff/MyFourthApp/good.kml   # Destination Google KML File

Readers:
- ACAD_1: ACAD from $(SourceDataset_ACAD) in EPSG:2277

Writers:
- OGCKML_1: OGCKML to $(DestDataset_OGCKML)

water_distribution_lines (reader ACAD_1)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
    -> GeometryFilter
GeometryFilter
    BREAK_AGG = No
    GEOM_PORT_NAMES = Line
    LINE -> GeometryValidator

Bookmark: Validation
GeometryValidator
    ISSUE_ATTR_NAME = _issues
    OGC_SIMPLE_CHECK = OGC_SIMPLE_CHECK
    OGC_VALID_CHECK = OGC_VALID_CHECK
    PRESETS = OGC
    REPAIR = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> water_distribution_lines (writer OGCKML_1)
    FAILED -> KMLStyler
KMLStyler
    COLOR = 1,0.192157,0.0313725
    FILL_OPACITY = 0.4
    ICON_OPACITY = 1.0
    ICON_SCALE = 0.8
    LABEL_OPACITY = 1.0
    LABEL_SCALE = 1.0
    LABEL_VISIBILITY = Yes
    LINE_WIDTH = 5
    LINE_WIDTH_UNITS = Pixels (Display Units)
    OPACITY = 1.0
    STYLE_PER_FEATURE = Yes
    KMLStyled -> water_distribution_lines (writer OGCKML_1)

Bookmark: KML
water_distribution_lines (writer OGCKML_1)
    attributes: ANNO_DIAM kml_char(4), COMPKEY kml_int16, COMPTYPE kml_int16, DIAMETER kml_int16, DRAW kml_int16, FEATURE_ID kml_char(25), LEAD_MAIN_ kml_int16, MATERIAL kml_char(8), PROJECT kml_char(9), PR_ZONE kml_char(4), STATUS kml_char(3), SYMCODE kml_int16, SYMCODE2 kml_int16, TILE kml_char(4), WNM_TYPE kml_char(8), YEAR_INSTA kml_int32, autocad_elevation kml_int16
