FME workspace webapp.bcroads.fmw

Parameters:
- GEOM = POLYGON((-123.31968482260129 49.05758039932133,-123.64927466635129 50.269944861577876,-119.33714087728879 50.34712582770931))   # " " Area of Interest

Writers:
- HTML_2: HTML to $(FME_MF_DIR)Output/BCTest/test1.html

Creator
    GEOMTYPE = Geometry Object
    NUM = 1
    CREATED -> GeometryReplacer_2
    CREATED -> HTTPCaller
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> DateTimeConverter
HTML (writer HTML_2)
    attributes: html_content buffer
DateTimeConverter__Rejected_: Inspector [off]

Bookmark: Gets User Input- Sets Coordindate System
GeometryReplacer_2
    KIND_LONG = OGC Well Known Text
    OGC_WKT_PRECISION_DISPLAY = 64-bit
    REMOVE_ATTRIBUTE = No
    SOURCE = $(GEOM)
    -> CoordinateSystemSetter_2
    <REJECTED> -> GeometryReplacer_2__Rejected_
CoordinateSystemSetter_2
    COORDSYS = LL84
    -> Clipper [CLIPPER]
GeometryReplacer_2__Rejected_: Inspector [off]

Bookmark: Drive BC API
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = http://api.open511.gov.bc.ca/events?format=json&status=ACTIVE
    TRANSFER_TIMEOUT_LENGTH = 90
    USE_COOKIES = No
    VERIFY_SSL_CERTIFICATES = Yes
    -> JSONFragmenter
    <Rejected> -> HTTPCaller__Rejected_
JSONFragmenter
    EXPLODE_FORMAT = JSON
    EXTRACT_ATTR = Yes
    JSON_ATTR = _response_body
    JSON_QUERY = json["events"][*]
    NEW_ATTRIBUTES = status headline description created updated
    RECURSIVE = Yes
    REJECT_EMPTY_LISTS = YES
    FRAGMENTS -> JSONFragmenter_2
    <REJECTED> -> JSONFragmenter__Rejected_
JSONFragmenter_2
    EXPLODE_FORMAT = JSON
    EXTRACT_ATTR = No
    JSON_ATTR = _response_body
    JSON_QUERY = json["geography"]
    REJECT_EMPTY_LISTS = YES
    FRAGMENTS -> GeometryReplacer
    <REJECTED> -> JSONFragmenter_2__Rejected_
GeometryReplacer
    ELLIPSOID_NAME = WGS84
    KIND_LONG = GeoJSON
    LETTERING = WGS84
    MSSQL_FORMAT_CHOICE = Geometry
    OGC_WKT_PRECISION_DISPLAY = 64-bit
    OUTPUT_POINT_DISPLAY = Point
    REMOVE_ATTRIBUTE = Yes
    SOURCE = @Value(_response_body)
    SRS_AXIS_ORDER_DISPLAY = Automatic
    -> CoordinateSystemSetter
    <REJECTED> -> GeometryReplacer__Rejected_
CoordinateSystemSetter
    COORDSYS = LL-WGS84
    -> Clipper [CLIPPEE]
GeometryReplacer__Rejected_: Inspector [off]
JSONFragmenter_2__Rejected_: Inspector [off]
JSONFragmenter__Rejected_: Inspector [off]
HTTPCaller__Rejected_: Inspector [off]

Bookmark: Formats HTML
DateTimeConverter
    DATETIME_ATTR = updated created
    OUT_FORMAT = %Y:%m:%d %H:%M:%S
    REPAIR_INPUT = NO
    -> HTMLReportGenerator
    <REJECTED> -> DateTimeConverter__Rejected_
HTMLReportGenerator
    CONTENT_LIST = HTML MAP_GOOGLE TABLE
    PAGE_CONFIG = HTML{{HTML;<h1> Drive BC Road and Weather Conditions </h1>;FME_CONTROLLER_QUERY_FILE;transformers/dependencies/html5/Custom HTML.fme}}MAP_GOOGLE{{LABEL;description;COLOR;252,31,28;TOKEN;AIzaSyD0PV4qXA9_Kjb_0hMu5sYHeeAMW8X2ApU;FME_CONTROLLER_QUERY_FILE;transformers/dependencies/html5/Map (Google).fme}}TABLE{{STYLE;CONDENSED;TABLE;status|Status/created|Created/updated|Updated/description|Description/headline|Headline;FME_CONTROLLER_QUERY_FILE;transformers/dependencies/html5/Table.fme}}
    TITLE = BC Drive API
    -> HTML (writer HTML_2)
