FME workspace transpose-bi.fmwt
Title: Transpose_BI

Parameters:
- SourceDataset_XLSXR = $(FME_MF_DIR)Data/CensusLocalAreaProfiles2011.xls   # Source Microsoft Excel File(s)
- DestDataset_CSV2 = $(FME_MF_DIR)Data\Output   # Destination CSV (Comma Separated Value) Folder

Readers:
- XLSXR_1: XLSXR from $(SourceDataset_XLSXR)

Writers:
- CSV2_1: CSV2 to $(DestDataset_CSV2)

Note: Excel document containing population statistics from the City of Vancouver
2011 Local Areas (reader XLSXR_1)
    attributes: A char(102), Arbutus-Ridge number(8,1), Downtown number(8,1), Dunbar-Southlands number(8,1), Fairview number(8,1), Grandview-Woodland number(8,1), Hastings-Sunrise number(8,1), Kensington-Cedar Cottage number(8,1), Kerrisdale number(8,1), Killarney number(8,1), Kitsilano number(8,1), Marpole number(8,1), Mount Pleasant number(8,1), Oakridge number(8,1), Renfrew-Collingwood number(8,1), Riley Park number(8,1), Shaughnessy number(7,1), South Cambie number(7,1), Strathcona number(8,1), Sunset number(8,1), Victoria-Fraserview number(8,1), West End number(8,1), West Point Grey number(8,1), Vancouver CSD (City) char(7), CMA of Vancouver char(8)
    -> Tester_2
Note: CSV Writer: 2011_Vancouver_Population
2011_Vancouver_Population (writer CSV2_1)
    attributes: StatType string, AreaName string, StatValue string

Bookmark: Filters and restructures data
Note: As we are only interested in the population totals, filters out the totals using the test, A Begins With Total.
Tester_2
    BOOL_OP = OR
    TEST_CLAUSE = TEST @Value(A) BEGINS_WITH Total
    TEST_MODE = Automatic
    TEST_DESCRIPTION = ""
    PASSED -> AttributeExploder
Note: Helps to restructure our data by creating one feature for each attribute value from the spreadsheet with a new pair of attributes (attribute name/attribute value). Attribute names become attribute values.
AttributeExploder
    KEEP_ATTRIBUTES = Yes
    ATTR_NAME_LABEL = _attr_name
    KEEP_GEOMETRY = No
    ATTR_VALUE_LABEL = _attr_value
    EXPLODING_TYPE = Features
    -> AttributeKeeper

Bookmark: Keep only the attributes we want in the output
Note: We only want to keep a selection of attributes. Keeps A, statistic type, _attr_name, Vancouver area boundaries, and _attr_value, population totals.
AttributeKeeper
    KEEP_ATTRS = A,_attr_name,_attr_value
    -> Tester
Note: Filters out unwanted attributes such as format attributes
Tester
    BOOL_OP = OR
    TEST_CLAUSE:
      TEST @Value(_attr_name) BEGINS_WITH xlsx_
      TEST @Value(_attr_name) BEGINS_WITH fme_
      TEST @Value(_attr_name) LIKE A
    TEST_MODE = Automatic
    TEST_DESCRIPTION = ""
    FAILED -> AttributeManager

Bookmark: Renames and filters attributes
Note: Renames attributes to more descriptive names / A -> StatType / _attr_name -> AreaName / _attr_value -> StatValue
AttributeManager
    ATTR_TABLE:
      RENAME_SET_VALUE A > StatType
      RENAME_SET_VALUE _attr_name > AreaName
      RENAME_SET_VALUE _attr_value > StatValue
    -> AttributeFilter
Note: Filters attributes by AreaName. This filters out statistics from the whole city of Vancouver as we are only interested in Vancouver area boundaries.
AttributeFilter
    ATTR_NAME = AreaName
    ATTR_VALUES = <EMPTY>,<MISSING>,<NULL>,<UNFILTERED>,CMA of Vancouver,Vancouver CSD (City)
    <UNFILTERED> -> 2011_Vancouver_Population (writer CSV2_1)
