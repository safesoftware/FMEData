FME workspace Attachments_Complete.fmwt
Title: Attachments_Complete

Parameters:
- SourceDataset_PATH = $(FME_MF_DIR)2/PointsOfInterest/Photos   # Source Directory and File Pathnames Directory
- DestDataset_GEODATABASE_FILE = $(FME_MF_DIR)Attachments.gdb   # Destination Esri File Geodatabase
- SourceDataset_GML = $(FME_MF_DIR)3/PointsOfInterest/POI.gml   # Source Geography Markup Language (GML) File(s)

Readers:
- PATH_1: PATH from $(SourceDataset_PATH)
- GML_1: GML from $(SourceDataset_GML)

Writers:
- GEODATABASE_FILE_1: GEODATABASE_FILE to $(DestDataset_GEODATABASE_FILE)

Note: Indicate Participation in / a Relationship Class
AttributeCreator
    ATTR_TABLE = SET_TO geodb_feature_has_relationships = yes
    -> Counter_2
Note: Create Feature ID
Counter_2
    SCOPE = Local
    CNT_ATTR = geodb_oid
    START = 1
    DOMAIN = counter
    -> AttributeRenamer_POIType
    -> AttributeRenamer_Origin

Bookmark: 2. Read Source Data
FireHalls (reader GML_1)
    attributes: gml_parent_id xml_buffer, HallNumber xml_char(30), Name xml_char(30), Address xml_char(30), PhoneNumber xml_char(30), Engine xml_char(1), Ladder xml_char(1), Quint xml_char(1), Rescue xml_char(1), Medic xml_char(1), gml_pointProperty xml_geometry, gml_multiPointProperty xml_geometry
    -> AttributeManager_3
CommunityCentres (reader GML_1)
    attributes: gml_parent_id xml_buffer, CentreName xml_char(30), CentreAddress xml_char(30), CentreURL xml_char(50), DocumentName xml_char(50), gml_pointProperty xml_geometry, gml_multiPointProperty xml_geometry
    -> AttributeManager_2
Libraries (reader GML_1)
    attributes: gml_parent_id xml_buffer, LibraryName xml_char(30), LibraryAddress xml_char(30), LibraryURL xml_char(50), DocumentName xml_char(50), gml_pointProperty xml_geometry, gml_multiPointProperty xml_geometry
    -> AttributeManager
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeCreator_2

Bookmark: 3. Setup Source attributes to match destination Schema
AttributeManager_3
    ATTR_TABLE:
      RENAME_SET_VALUE Name > Description
      RENAME_SET_VALUE HallNumber > Name
      RENAME_SET_VALUE Address > Street
      RENAME_SET_VALUE PhoneNumber > Phone
      SET_TO PostalCode = unknown
    -> AttributeCreator
AttributeManager_2
    ATTR_TABLE:
      RENAME_SET_VALUE CentreName > Name
      RENAME_SET_VALUE CentreAddress > Street
      RENAME_SET_VALUE CentreURL > Website
      RENAME_SET_VALUE DocumentName > Description
      SET_TO PostalCode = unknown
    -> AttributeCreator
Note: Setup the schema to match the destination tables
AttributeManager
    ATTR_TABLE:
      RENAME_SET_VALUE LibraryName > Name
      RENAME_SET_VALUE LibraryAddress > Street
      RENAME_SET_VALUE LibraryURL > Website
      RENAME_SET_VALUE DocumentName > Description
      SET_TO PostalCode = unknown
    -> AttributeCreator

Bookmark: 5. Connect Schema
Note: Rename fme_feature_type to POIType
AttributeRenamer_POIType
    ATTR_TABLE = RENAME_SET_DEFAULT fme_feature_type > POIType
    -> GUIDGenerator
Note: Use this custom transformer to / calculate GUID values
GUIDGenerator
    -> PointsOfInterest (writer GEODATABASE_FILE_1)

Bookmark: 9. Write Relationship & Attachments
Note: Output Point features
PointsOfInterest (writer GEODATABASE_FILE_1)
    attributes: Name char(50), POIType char(50), Street char(50), City char(50), State char(5), Country char(50), PostalCode char(7), Description char(100), Phone char(10), Website char(80), geodb_oid integer, GUID char(38)
Note: Output to the relationship / table
PointsOfInterest__ATTACHREL (writer GEODATABASE_FILE_1)
Note: Write to Attachments table / filling the required fields
PointsOfInterest__ATTACH (writer GEODATABASE_FILE_1)
    attributes: geodb_oid integer, ATTACHMENTID integer, REL_OBJECTID integer, CONTENT_TYPE char(150), ATT_NAME char(250), DATA_SIZE integer, DATA blob

Bookmark: 6. Add relationship related attributes
Note: Set as Origin of Relationship
Note: Setup the relationship attributes / - geodb_rel_origin_oid / - geodb_rel_destination_oid
AttributeRenamer_Origin
    ATTR_TABLE = RENAME_SET_DEFAULT geodb_oid > geodb_rel_origin_oid
    -> FeatureMerger [REQUESTOR]
Note: Set as Destination of Relationship
AttributeRenamer_Destination
    ATTR_TABLE = RENAME_SET_DEFAULT geodb_oid > geodb_rel_destination_oid
    -> FeatureMerger [SUPPLIER]

Bookmark: 4. Add relationship related attributes
Note: Indicate Participation in / a Relationship Class
Note: Setup the relationship attributes / - geodb_feature_has_relationships / - geodb_oid
AttributeCreator_2
    ATTR_TABLE = SET_TO geodb_feature_has_relationships = yes
    -> Counter_3
Note: Create Feature ID
Counter_3
    SCOPE = Local
    CNT_ATTR = geodb_oid
    START = 1
    DOMAIN = counter
    -> AttributeRenamer_Destination
    -> AttributeCopier

Bookmark: 7. Build the relationship information
Note: Setup the 1:M relationship using the list of matches to create the additional features.
FeatureMerger
    LIST_NAME = Docs
    PROCESS_DUPS = Yes
    ATTR_CONFLICT_RES = Use Requestor
    JOIN_KEYS = @Value(Name) @Value(path_rootname) AUTO
    LIST_ATTRS_TO_INCLUDE = path_filename geodb_rel_destination_oid
    ATTR_ACCUM_MODE = Merge Supplier
    SUPPLIERS_FIRST = No
    MERGE_TYPE = Attributes Only
    REJECT_NULL_MISSING_KEYS = No
    CONNECT_Z_MODE = First Wins
    IGNORE_NULLS = No
    GEOM_TYPE = Build Polygons
    MERGED -> ListExploder
ListExploder
    ATTR_ACCUM_MODE = Merge List Attributes
    LIST_ATTR = Docs{}
    ATTR_CONFLICT_RES = Use List Attribute Values
    INDEX_ATTR = _element_index
    ELEMENTS -> AttributeCreator_3
AttributeCreator_3
    ATTR_TABLE = SET_TO geodb_type = geodb_relationship
    -> PointsOfInterest__ATTACHREL (writer GEODATABASE_FILE_1)

Bookmark: 8. Setup the fields in the Attachment table
AttributeCopier
    ATTR_TABLE:
      COPY geodb_oid > REL_OBJECTID
      COPY path_filename > ATT_NAME
      COPY path_filesize > DATA_SIZE
      COPY path_extension > CONTENT_TYPE
    -> StringConcatenator
StringConcatenator
    VAL_ATTR = CONTENT_TYPE
    PARM_LINE = image/p.@Value(path_extension)
    ACTION = Create New Attribute
    -> AttributeFileReader
Note: Read attachments into an attribute
AttributeFileReader
    DEST_ATTR = DATA
    FILE_NAME = @Value(path_windows)
    CHAR_ENCODING = fme-binary
    -> PointsOfInterest__ATTACH (writer GEODATABASE_FILE_1)

Bookmark: 4. Add relationship related attributes
Note: Setup the relationship attributes / - geodb_feature_has_relationships / - geodb_oid

FME custom transformer GUIDGenerator
Creates an ESRI GUID ID by creating a UUID and concatenating {} to it.
This custom transformer will add a GFID attribute to input features.

INPUT (input)
    -> UUIDGENERATOR_2
Note: Create UUID
UUIDGENERATOR_2: UUIDGenerator
    UUID_ATTR = GUID
    -> CONCATENATOR_2
Note: Put the UUID in {}
CONCATENATOR_2: StringConcatenator
    VAL_ATTR = GUID
    PARM_LINE = {@Value(GUID)}
    ACTION = Create New Attribute
    -> OUTPUT (output)
OUTPUT (output)
