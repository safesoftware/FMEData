FME workspace One2ManyStartWorkspace.fmwt
Title: One2ManyStartWorkspace

Readers:
- GEODATABASE_FILE_2: GEODATABASE_FILE from $(FME_MF_DIR)1/wb_template_1582581464299_63956/1ManyRelationshipStart.gdb

A_Neighborhoods (reader GEODATABASE_FILE_2)
    attributes: OBJECTID integer, ID double, NAME char(20), URL char(60), POP2001 double, POP2011 double, GFID guid, SHAPE_Length double, SHAPE_Area double
A_A_Parcels (reader GEODATABASE_FILE_2)
    attributes: OBJECTID integer, PARCELID integer, GFID guid, Shape_Length double, Shape_Area double, NeighbourID integer
