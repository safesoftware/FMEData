FME workspace FeatureReaderToQueryAGeodatabase.fmw
Title: FeatureReader to Query a Geodatabase

Parameters:
- SourceDataset_GEODATABASE_FILE =

Readers:
- GEODATABASE_FILE_1: GEODATABASE_FILE from $(SourceDataset_GEODATABASE_FILE)

Grid (reader GEODATABASE_FILE_1)
    attributes: OBJECTID integer, GridId double, FacetText char(3), Grid_Text integer, SHAPE_Length double, SHAPE_Area double
    -> FeatureReader [INITIATOR]
    -> Inspector_2
FeatureReader
    ATTRIBUTES = AddressPoints,"OBJECTID,AddressId,CivicNo,StreetName,TaxCoord,SiteId,PostalAddressId,PostalAddress,PostalCity,PostalProvince,PostalCode,Country,Status,LastUpdate,LastEditor",Grid,"OBJECTID,GridId,FacetText,Grid_Text,SHAPE_Length,SHAPE_Area"
    ATTR_ACCUM_MODE = Only Use Result
    COMBINE_GEOM = Use Result
    DATASET = $(FME_MF_DIR_ENCODED)Database_Tranformers.gdb
    FEATURETYPES = AddressPoints
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_RESOLVE_DOMAINS = no
    GEODATABASE_FILE_RESOLVE_SUBTYPE_NAMES = yes
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INTERACT = CONTAINS
    OUTPUT_FEATURES_DISPLAY = Schema and Data Features
    AddressPoints -> Inspector
Inspector
Inspector_2
