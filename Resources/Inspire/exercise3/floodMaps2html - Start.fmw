FME workspace floodMaps2html - Start.fmw

Parameters:
- BUFFER = 20   # Buffer amount
- LONGITUDE = -1.8
- LATITUDE = 52.7
- WARNINGTYPE = Past   # Warning Type
- IMPACTTYPE = None   # Impact Type
- DestDataset_HTML = $(FME_MF_DIR)results\maps\mapApp.html   # HTML Files(*.html)|*.html Destination Html File

Writers:
- HTML_1: HTML to $(DestDataset_HTML)

HTML (writer HTML_1)
    attributes: html_content buffer

Bookmark: 1. Read Flood data
Creator_3
    GEOMTYPE = Geometry Object
    NUM = 1
    CREATED -> TestFilter_2
TestFilter_2
    DEFAULT_VALUE = Current
    TEST_LIST = "BOOL_OP,OR,COMPOSITE_TEST,""""""1"""""",TEST_CLAUSE,TEST $(WARNINGTYPE) = Past",Past
    Past -> FeatureReader_4 [INITIATOR]
    Current -> FeatureReader_5 [INITIATOR]
FeatureReader_5
    ATTRIBUTES = floods,"_featureType,_fileName,_date,_timestamp,_length,_http_status_code,floodAreaID,description,message,severity,severityLevel"
    ATTR_ACCUM_MODE = Only Use Result
    COMBINE_GEOM = Use Result
    DATASET = C:\Users\dhintz\Dropbox (Safe Software Inc.)\DeanSafe\Projects\_StrategicProjects\INSPIRE\Conferences\INSPIRE.Helsinki2019\DataChallenge\exercises\exercise2\results\currentFloods.gpkg
    FEATURETYPES = floods
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    GEOPACKAGE_USE_SEARCH_ENVELOPE = NO
    INTERACT = <No Spatial Filter>
    OUTPUT_FEATURES_DISPLAY = Schema and Data Features
    floods -> AttributeCreator_3
FeatureReader_4
    ATTRIBUTES = floods,"_featureType,_fileName,_date,_timestamp,_length,_http_status_code,floodAreaID,description,message,severity,severityLevel"
    ATTR_ACCUM_MODE = Only Use Result
    COMBINE_GEOM = Use Result
    DATASET = C:\Users\dhintz\Dropbox (Safe Software Inc.)\DeanSafe\Projects\_StrategicProjects\INSPIRE\Conferences\INSPIRE.Helsinki2019\DataChallenge\exercises\exercise1\results\pastFloods.gpkg
    FEATURETYPES = floods
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    GEOPACKAGE_USE_SEARCH_ENVELOPE = NO
    INTERACT = <No Spatial Filter>
    OUTPUT_FEATURES_DISPLAY = Schema and Data Features
    floods -> SpatialFilter [Candidate]

Bookmark: 4. Filter Floods
AttributeCreator_3
    ATTR_TABLE = SET_TO queryWarningLevel = FME_CONDITIONAL:DEFAULT_VALUE'2'BOOL_OP;OR;COMPOSITE_TEST;1;CASE_INSENSITIVE_TEST $(WARNINGTYPE) CONTAINS Expired'4'BOOL_OP;AND;COMPOSITE_TEST;1;CASE_INSENSITIVE_TEST $(WARNINGTYPE) CONTAINS Alert'3'FME_NUM_CONDITIONS3___
    -> Tester
Tester
    BOOL_OP = OR
    COMPOSITE_TEST = 1
    TEST_CLAUSE = CASE_INSENSITIVE_TEST @Value(severityLevel) <= @Value(queryWarningLevel)
    TEST_MODE = CASE_INSENSITIVE_TEST
    PASSED -> SpatialFilter [Candidate]
SpatialFilter
    AGGREGATE_HANDLING = Yes
    ATTR_ACCUM_MODE = Prefix Filter
    ATTR_PREFIX = filter_
    BASE_TYPE = Multiple Filters
    CURVE_BOUNDARY_RULE_PARAM = Default Rule
    PASS_CRITERIA = Pass Against One Filter
    PREDATTR = _predicate
    PREDICATES = INTERSECTS
    USE_BOUNDING_BOX = No
    PASSED -> CoordinateExtractor
    PASSED -> BulkAttributeRemover

Bookmark: 2. Create Query Feature
Creator
    COORDSYS = LL84
    GEOMTYPE = Geometry Object
    NUM = 1
    CREATED -> VertexCreator
VertexCreator
    MEASURE_TYPE = Continuous
    MISSING_VAL_MODE = Compute
    MODE_NAME = Add Point
    XVAL = $(LONGITUDE)
    YVAL = $(LATITUDE)
    -> GeographicBufferer
GeographicBufferer
    ANGLE = 22.5
    BufferDist = $(BUFFER)
    BufferUnit = Kilometers
    CAP_STYLE = Round
    CORNER_STYLE = Round
    MITER_LIMIT = 1
    -> AttributeCreator_2
AttributeCreator_2
    ATTR_TABLE:
      SET_TO buffer = $(BUFFER)
      SET_TO warningType = $(WARNINGTYPE)
      SET_TO lat = $(LATITUDE)
      SET_TO long = $(LONGITUDE)
      SET_TO floodAreaID = area of interest
      SET_TO description = selection area
    -> SpatialFilter [Filter]
    -> FeatureMerger [SUPPLIER]
    -> FeatureMerger_2 [SUPPLIER]
    -> Clipper [CLIPPER]
    -> FeatureMerger_3 [SUPPLIER]

Bookmark: 6. Generate Flood Output Schema and Values; Format HTML Output
CoordinateExtractor
    IND = 0
    MODE = Specify Coordinate
    X_ATTR = lat
    Y_ATTR = long
    Z_ATTR = _z
    -> AttributeRounder
AttributeRounder
    PLACES = 3
    ROUND_TYPE = Nearest
    SRC_ATTRS = long lat
    -> AttributeCreator
AttributeCreator
    ATTR_TABLE = SET_TO _label = Flood @Value(floodAreaID) Date @Value(_date) @Value(description)
    -> HTMLReportGenerator
    -> NoFeaturesTester
NoFeaturesTester
    NOINPUT -> FeatureMerger [REQUESTOR]
FeatureMerger
    ATTR_ACCUM_MODE = Merge Supplier
    ATTR_CONFLICT_RES = Use Requestor
    IGNORE_NULLS = No
    JOIN_KEYS = 1 1 AUTO
    MERGE_TYPE = Attributes and Geometry
    PROCESS_DUPS = NO
    REJECT_NULL_MISSING_KEYS = No
    SUPPLIERS_FIRST = No
    MERGED -> AttributeCreator_4
AttributeCreator_4
    ATTR_TABLE:
      SET_TO lat = $(LATITUDE)
      SET_TO long = $(LONGITUDE)
      SET_TO floodAreaID = $(WARNINGTYPE)
      SET_TO description = No flood warning data available for your area of interest
      SET_TO _label = Area of Interest - no data. WarningType: $(WARNINGTYPE), Impact type: $(IMPACTTYPE)
    -> HTMLReportGenerator
HTMLReportGenerator
    CONTENT_LIST = MAP_ESRI TABLE
    PAGE_CONFIG = MAP_ESRI{{LABEL;_label;COLOR;0,170,255;BASEMAP;Streets;URLS;http://www.safe.com;FME_CONTROLLER_QUERY_FILE;transformers/dependencies/html5/Map (Esri Leaflet).fme}}TABLE{{STYLE;DEFAULT;TABLE;floodAreaID|Flood area ID/_date|Flood warning date/description|Flood description/severity|Severity/severityLevel|Severity level/long|Longitude/lat|Latitude/_timestamp|Time loaded;FME_CONTROLLER_QUERY_FILE;transformers/dependencies/html5/Table.fme}}
    TITLE = Current Floods
    -> Tester_3
Tester_3
    BOOL_OP = OR
    COMPOSITE_TEST = 1
    TEST_CLAUSE = TEST $(IMPACTTYPE) = None
    TEST_MODE = TEST
    PASSED -> HTML (writer HTML_1)

Bookmark: 5. Filter Impacts
BulkAttributeRemover
    ATTR_EXP = filter_*
    -> GeographicBufferer_2
GeographicBufferer_2
    ANGLE = 22.5
    BufferDist = 100
    BufferUnit = Meters
    CAP_STYLE = Round
    CORNER_STYLE = Round
    MITER_LIMIT = 1
    -> SpatialFilter_2 [Filter]
    -> SpatialFilter_3 [Filter]
SubstringExtractor
    END = 30
    RESULT_ATTR = _roadName
    SRC_STRING = @Value(_roadName)
    START = 0
    -> SpatialFilter_2 [Candidate]
SpatialFilter_2
    AGGREGATE_HANDLING = Yes
    ATTR_ACCUM_MODE = Prefix Filter
    ATTR_PREFIX = filter_
    BASE_TYPE = Multiple Filters
    CURVE_BOUNDARY_RULE_PARAM = Default Rule
    PASS_CRITERIA = Pass Against One Filter
    PREDATTR = _predicate
    PREDICATES = TOUCHES INTERSECTS WITHIN
    USE_BOUNDING_BOX = No
    PASSED -> AttributeCreator_5
SpatialFilter_3
    AGGREGATE_HANDLING = Yes
    ATTR_ACCUM_MODE = Prefix Filter
    ATTR_PREFIX = filter_
    BASE_TYPE = Multiple Filters
    CURVE_BOUNDARY_RULE_PARAM = Default Rule
    PASS_CRITERIA = Pass Against One Filter
    PREDATTR = _predicate
    PREDICATES = TOUCHES INTERSECTS WITHIN
    USE_BOUNDING_BOX = No
    PASSED -> AttributeCreator_7

Bookmark: 3. Read impact layers if selected
Creator_2
    GEOMTYPE = Geometry Object
    NUM = 1
    CREATED -> TestFilter
TestFilter
    DEFAULT_VALUE = None
    TEST_LIST = "BOOL_OP,OR,COMPOSITE_TEST,""""""1"""""",TEST_CLAUSE,TEST $(IMPACTTYPE) = Roads",Roads,"BOOL_OP,OR,COMPOSITE_TEST,""""""1"""""",TEST_CLAUSE,TEST $(IMPACTTYPE) = Junctions",Junctions
    Roads -> FeatureReader [INITIATOR]
    Junctions -> FeatureReader_2 [INITIATOR]
    None -> TestFilter_None
FeatureReader
    ATTRIBUTES = junctions,"gml_parent_id,gml_id,junctionNumber",roads,"_roadName,gml_parent_id,gml_id,inspireId_Identifier_localId,inspireId_Identifier_namespace,inspireId_Identifier_versionId,inspireId_Identifier_versionId_nilReason,inspireId_Identifier_versionId_xsi_nil,validFrom,validFrom_nilReason,validFrom_xsi_nil,validTo,validTo_nilReason,validTo_xsi_nil,roadClassification,roadClassification_codeSpace,roadFunction,roadFunction_codeSpace,formOfWay,roadClassificationNumber,name1,name1_xml_lang,name2,name2_xml_lang,length,length_uom,primaryRoute,trunkRoad"
    ATTR_ACCUM_MODE = Only Use Result
    COMBINE_GEOM = Use Result
    DATASET = ..\exercise1\results\majorRoads.gpkg
    FEATURETYPES = roads
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    GEOPACKAGE_USE_SEARCH_ENVELOPE = NO
    INTERACT = <No Spatial Filter>
    OUTPUT_FEATURES_DISPLAY = Schema and Data Features
    roads -> SubstringExtractor
FeatureReader_2
    ATTRIBUTES = junctions,"gml_parent_id,gml_id,junctionNumber",roads,"_roadName,gml_parent_id,gml_id,inspireId_Identifier_localId,inspireId_Identifier_namespace,inspireId_Identifier_versionId,inspireId_Identifier_versionId_nilReason,inspireId_Identifier_versionId_xsi_nil,validFrom,validFrom_nilReason,validFrom_xsi_nil,validTo,validTo_nilReason,validTo_xsi_nil,roadClassification,roadClassification_codeSpace,roadFunction,roadFunction_codeSpace,formOfWay,roadClassificationNumber,name1,name1_xml_lang,name2,name2_xml_lang,length,length_uom,primaryRoute,trunkRoad"
    ATTR_ACCUM_MODE = Only Use Result
    COMBINE_GEOM = Use Result
    DATASET = ..\exercise1\results\majorRoads.gpkg
    FEATURETYPES = junctions
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    GEOPACKAGE_USE_SEARCH_ENVELOPE = NO
    INTERACT = <No Spatial Filter>
    OUTPUT_FEATURES_DISPLAY = Schema and Data Features
    junctions -> SpatialFilter_3 [Candidate]
TestFilter_None: Logger
    LOG_FEATURE = LOG_ONLY
    MAXCOORDS = 20
    MAXFEATS = 20
    MESSAGE = Feature is:
    SEVERITY = INFO

Bookmark: 7. Generate Impact Output Schema and Values; Format HTML Output
AttributeCreator_5
    ATTR_TABLE = SET_TO _label = Road @Value(_roadName) Flood @Value(filter_floodAreaID) Date @Value(filter__date)
    -> Clipper [CLIPPEE]
    -> FeatureMerger_2 [REQUESTOR]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> HTMLReportGenerator_2
FeatureMerger_2
    ATTR_ACCUM_MODE = Merge Supplier
    ATTR_CONFLICT_RES = Use Requestor
    IGNORE_NULLS = No
    JOIN_KEYS = 1 1 AUTO
    MERGE_TYPE = Attributes and Geometry
    PROCESS_DUPS = NO
    REJECT_NULL_MISSING_KEYS = No
    SUPPLIERS_FIRST = No
    MERGED -> NoFeaturesTester_2
AttributeCreator_7
    ATTR_TABLE = SET_TO _label = Junction @Value(junctionNumber) Flood @Value(filter_floodAreaID) Date @Value(filter__date)
    -> GeographicBufferer_3
GeographicBufferer_3
    ANGLE = 22.5
    BufferDist = 333
    BufferUnit = Meters
    CAP_STYLE = Round
    CORNER_STYLE = Round
    MITER_LIMIT = 1
    -> HTMLReportGenerator_3
HTMLReportGenerator_3
    CONTENT_LIST = MAP_ESRI TABLE
    PAGE_CONFIG = MAP_ESRI{{LABEL;_label;COLOR;255,0,0;BASEMAP;Streets;URLS;http://www.safe.com;FME_CONTROLLER_QUERY_FILE;transformers/dependencies/html5/Map (Esri Leaflet).fme}}TABLE{{STYLE;DEFAULT;TABLE;junctionNumber|Junction/gml_id|Junction ID/filter_floodAreaID|Flood area ID/filter__date|Flood warning date/filter_severity|Flood severity/filter_severityLevel|Flood severity Level/filter_description|Flood description;FME_CONTROLLER_QUERY_FILE;transformers/dependencies/html5/Table.fme}}
    TITLE = Flood Affected Road Junctions
    -> Tester_2
    -> NoFeaturesTester_2
NoFeaturesTester_2
    NOINPUT -> AttributeCreator_6
AttributeCreator_6
    ATTR_TABLE:
      SET_TO _roadName = $(WARNINGTYPE)
      SET_TO filter_floodAreaID = area of interest
      SET_TO filter_description = No data available for flood affected $(IMPACTTYPE) in your area of interest
      SET_TO _label = Area of Interest - no data. WarningType: $(WARNINGTYPE), Impact type: $(IMPACTTYPE)
    -> FeatureMerger_3 [REQUESTOR]
FeatureMerger_3
    ATTR_ACCUM_MODE = Merge Supplier
    ATTR_CONFLICT_RES = Use Requestor
    IGNORE_NULLS = No
    JOIN_KEYS = 1 1 AUTO
    MERGE_TYPE = Attributes and Geometry
    PROCESS_DUPS = NO
    REJECT_NULL_MISSING_KEYS = No
    SUPPLIERS_FIRST = No
    MERGED -> HTMLReportGenerator_2
HTMLReportGenerator_2
    CONTENT_LIST = MAP_ESRI TABLE
    PAGE_CONFIG = MAP_ESRI{{LABEL;_label;COLOR;0,0,0;BASEMAP;Streets;URLS;http://www.safe.com;FME_CONTROLLER_QUERY_FILE;transformers/dependencies/html5/Map (Esri Leaflet).fme}}TABLE{{STYLE;DEFAULT;TABLE;_roadName|Road name/roadClassification|Road classification/gml_id|Road ID/filter_floodAreaID|Flood area ID/filter__date|Flood warning date/filter_severity|Flood severity/filter_severityLevel|Flood severity level/filter_description|Flood description;FME_CONTROLLER_QUERY_FILE;transformers/dependencies/html5/Table.fme}}
    TITLE = Flood Affected Roads
    -> Tester_2
Tester_2
    BOOL_OP = OR
    COMPOSITE_TEST = 1
    TEST_CLAUSE = TEST $(IMPACTTYPE) != None
    TEST_MODE = TEST
    PASSED -> HTML (writer HTML_1)

FME custom transformer NoFeaturesTester
Description
This transformer checks whether there are any input features. If not, then a single feature is ouput via the NOINPUT port. If INPUT features exist, then they are output via the INPUT output port.
Other transformers often generate features that signify an error condition. This transformer can be used to check for those features and if those features exists, then a separate action can be triggered.
Example 
This may be useful to test if any data emerges from a reader, when the 'Ignore Failed Readers' advanced parameter is set to yes.
Input Ports 
Input: Features to be checked for existence. Any features will be accepted. 
Output Ports
NoInput:
If no input features exist, a single featue is returned via the NoInput port. 
Output: 
Any feature that entered the Input port is returned via the Output port.

INPUT (input)
    -> Sampler
    -> OUTPUT (output)
OUTPUT (output)
Sampler
    RATE = 1
    SAMPLE_MODE = No
    SAMPLE_TYPE_LONG = First N Features
    SAMPLED -> AttributeCreator_2
AttributeCreator_2
    ATTR_TABLE:
      SET_TO count = 0
      SET_TO remove = yes
    -> DuplicateFilter
Creator
    GEOMTYPE = Geometry Object
    NUM = 1
    CREATED -> AttributeCreator_3
AttributeCreator_3
    ATTR_TABLE = SET_TO no_features = true
    -> DuplicateFilter
DuplicateFilter
    INPUT_ORDERED_CHOICE = No
    KEYATTR = count
    UNIQUE -> Tester
Tester
    BOOL_OP = OR
    COMPOSITE_TEST = 1
    TEST_CLAUSE = TEST @Value(remove) != yes
    TEST_MODE = TEST
    PASSED -> AttributeRemover
AttributeRemover
    REMOVE_ATTRS = count,remove
    -> NOINPUT (output)
NOINPUT (output)
