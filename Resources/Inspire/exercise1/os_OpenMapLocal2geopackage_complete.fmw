FME workspace os_OpenMapLocal2geopackage_complete.fmw

Parameters:
- DestDataset_GEOPACKAGE = .\results\infrastructure.gpkg   # GeoPackage File
- SourceDataset_GML = ""$(FME_MF_DIR)source_setup\OSOpenMapLocal_SJ.gml" "$(FME_MF_DIR)source_setup\OSOpenMapLocal_SO.gml""   # Source Geography Markup Language (GML) File(s)

Readers:
- GML_1: GML from $(SourceDataset_GML)

Writers:
- GEOPACKAGE_1: GEOPACKAGE to $(DestDataset_GEOPACKAGE) in LL84

ElectricityTransmissionLine (reader GML_1)
    attributes: geometry xml_geometry, featureCode xml_int64
    -> AttributeCreator
CarChargingPoint (reader GML_1)
    attributes: featureCode xml_int64, chargeMethod xml_buffer, chargeMethod.codeSpace xml_buffer, geometry xml_geometry, ratedVoltage xml_buffer, ratedVoltage.codeSpace xml_buffer, type xml_buffer, type.codeSpace xml_buffer
    -> AttributeCreator
FeatureCollection (reader GML_1) [off]
    attributes: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
ImportantBuilding (reader GML_1)
    attributes: distinctiveName xml_buffer, buildingTheme xml_buffer, buildingTheme.codeSpace xml_buffer, classification xml_buffer, classification.codeSpace xml_buffer, geometry xml_geometry, featureCode xml_int64
    -> AttributeCreator
RoadTunnel (reader GML_1)
    attributes: geometry xml_geometry, featureCode xml_int64
    -> AttributeCreator
RailwayStation (reader GML_1)
    attributes: distinctiveName xml_buffer, classification xml_buffer, classification.codeSpace xml_buffer, geometry xml_geometry, featureCode xml_int64
    -> AttributeCreator
RailwayTrack (reader GML_1) [off]
    attributes: classification xml_buffer, classification.codeSpace xml_buffer, geometry xml_geometry, featureCode xml_int64
    -> AttributeCreator
RailwayTunnel (reader GML_1)
    attributes: geometry xml_geometry, featureCode xml_int64
    -> AttributeCreator
Note: FunctionalSite: OSOpenMapLocal_SO [GML]
Note: Tiles SJ, SK, SO, SP for central England
Note: C:\Temp\UKOS\oproad_gml3_gb\data
FunctionalSite (reader GML_1)
    attributes: distinctiveName xml_buffer, siteTheme xml_buffer, siteTheme.codeSpace xml_buffer, classification xml_buffer, classification.codeSpace xml_buffer, geometry xml_geometry, featureCode xml_int64
    -> AttributeCreator
AttributeCreator
    ATTR_TABLE:
      SET_TO infrastructureType = @Value(fme_feature_type)
      SET_TO source = @Value(gml_parent_id)
    -> CsmapReprojector
CsmapReprojector
    DEST = LL84
    INTERPOLATION_TYPE_NAME = Nearest Neighbor
    RASTER_CELL_SIZE = Preserve Cells
    RASTER_TOLERANCE = 0.0
    VERTICAL_HANDLING = Ignore heights and leave them unchanged
    REPROJECTED -> AttributeKeeper
AttributeKeeper
    KEEP_ATTRS = siteTheme,buildingTheme,source,infrastructureType,distinctiveName,featureCode,classification,gml_id,type
    -> infrastructure (writer GEOPACKAGE_1)
infrastructure (writer GEOPACKAGE_1)
    attributes: infrastructureType text(200), source text(200), gml_id text, distinctiveName text, siteTheme text, classification text, featureCode int, buildingTheme text, type text
