FME workspace DecodeQuestion1.fmw

Creator
    NUM = 1
    GEOMTYPE = Geometry Object
    CREATED -> AttributeManager
AttributeManager
    ATTR_TABLE = SET_TO text = .6 si ecnetnes siht rof rebmun edoc ehT .rebmun edoc a dnif ot gnidoced ralimis sdeen ecnetnes hcaE .ylreporp ti tamrof ot EMF esu ot si egnellahc eht ,yawyna daer ylbaborp dluoc uoy ecnetnes eno si siht hguohtlA .snoitalutargnoC
    -> PythonCaller
PythonCaller
    PYTHONSOURCE:
      import fme
      import fmeobjects
      # Template Function interface:
      # When using this function, make sure its name is set as the value of
      # the 'Class or Function to Process Features' transformer parameter
      def processFeature(feature):
      	feature.setAttribute('result', feature.getAttribute('text')[::-1])
    PYTHONSYMBOL = processFeature
    NEW_ATTRIBUTES = result
    -> PythonCaller_Output
PythonCaller_Output: Inspector
