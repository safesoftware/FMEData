FME workspace SelfServeApps_Complete.fmw

Parameters:
- DestDataset_HTML = C:\Users\dan.minney_safe\Documents\Projects\Cityworks\Live Training\Article Updates\Sending a Work Order to Cityworks\CreateAWorkOrder\WorkOrderReport.html   # Destination Html File
- _attachment =   # "" Attachment
- SourceDataset_XLSXR_3 = $(FME_MF_DIR)WorkOrderAddresses.xlsx   # Source Microsoft Excel File(s)

Readers:
- XLSXR_2: XLSXR from $(SourceDataset_XLSXR_3)

Writers:
- HTML_1: HTML to $(DestDataset_HTML)

WorkOrders (reader XLSXR_2)
    attributes: Address char(24), Entity Type char(18), Template ID number(2,0)
    -> WorkOrderCreator
WorkOrderCreator
    _authentication = Cityworks 23 Connection
    _entity_type = @Value(Entity Type)
    _instance = https://your-cityworks-instance/cityworks
    _request_params = "Priority":"3","Address":"@Value(Address)"
    _wo_template_id = @Value(Template ID)
    -> WorkOrderAttachmentAdder
WorkOrderAttachmentAdder
    _attachment = $(_attachment)
    _authentication = Cityworks 23 Connection
    _instance = http://your-cityworks-instance/cityworks
    _workorderid = @Value(_work_order_id)
    -> HTMLReportGenerator
HTMLReportGenerator
    CONTENT_LIST = TABLE
    PAGE_CONFIG = TABLE{{STYLE;DEFAULT;TABLE;_work_order_id|Work Order ID/_address|Address;FME_CONTROLLER_QUERY_FILE;transformers/dependencies/html5/Table.fme;FME_CONTROLLER_CHOICE;Table}}
    TITLE = Work Order Report
    -> HTML (writer HTML_1)
HTML (writer HTML_1)
    attributes: html_content buffer

FME custom transformer WorkOrderCreator
Description
This transformer leverages the Cityworks REST API to create work orders within Cityworks from FME. It is designed to be used with an authenticated web connection to Cityworks.
Details
The transformer is designed to require only the essential parameters to create a work order in Cityworks with an option to include additional parameters. An HTTPCaller is used to make the call to the Cityworks API, followed by a JSONExtractor to extract valuable information from the response. Further configuration of the JSONExtractor can allow you to pull out more attributes from the response based on your custom needs. Similarly, additional parameters can be provided in the Additional Request Parameters field to send a more detailed request to Cityworks. 
The User Parameter for_entity_type and _wo_template_id may need configuration to reflect the details of your Cityworks instance.
Input Ports
Features entering this port trigger the creation of one work order. Incoming attribute values may be used as input if they are valid parameters of the request URL. If this transformer is intended to be used on its own, a Creator transformer should be used as input to trigger the call without having to read in data.
Output Ports
The outgoing feature carries a _work_order_id attribute, which is the ID of the work order created in Cityworks. Outgoing attributes include all input parameters plus the JSON response body, and work order ID. Further attributes can be output by configuring the JSONExtractor inside the transformer to parse the response from Cityworks.
There is also a rejected output port that is connected to the HTTPCaller. Further transformers can be connected to the rejected output from inside the custom transformer. Simply create connections between the transformers and the input of the rejected port.
Parameters
Web Connection: The name of your Cityworks web connection.
Cityworks Instance: The path to your Cityworks instance endpoint.
Example: http://localhost/Cityworks
Entity Type: This parameter is required by all work order creation calls to the Cityworks API. It relates to the issue that requires attention. Example: Streets or Pavement
Work Order Template ID: This parameter is required by all work order creation calls to the Cityworks API. This parameter will create the work order with a specific template of questions relating to your Entity Type.
Additional Request Parameters: This parameter can contain one or more extra request parameter definitions which will be included in your work order. Parameters must be valid for your Cityworks instance. Additional parameters should be formatted with double quotation marks (") surrounding each key and value, with a colon (:) between keys and values. Each key-value pair should be separated by a comma (,).
Example: ''Address'':''1234 Fake St.'',''City'':''NowhereVille''
Consult your Cityworks documentation for more request parameters.

Parameters:
- _authentication =   # Web Services","HDFS Insecure Client","HDFS Delegation Token","HDFS Kerberos" Web Connection
- _instance =   # Cityworks Instance
- _entity_type =   # Entity Type
- _wo_template_id =   # "" Work Order Template ID
- _request_params = "Priority":"3"   # Additional Request Parameters

Input (input)
    -> ParameterFetcher
ParameterFetcher
    ATTR_LIST = _entity_type $(_entity_type) _request_params $(_request_params) _authentication $(_authentication) _instance $(_instance) _wo_template_id $(_wo_template_id)
    -> AttributeKeeper
AttributeKeeper
    CREATE_BULK_MODE_FEATURES = No
    KEEP_ATTRS = _address,_entity_type,_instance,_request_params,_wo_template_id,_authentication
    -> CreateWorkOrder
Output (output)
<Rejected> (output)

Bookmark: Create Work Order and clean up output attributes
CreateWorkOrder: HTTPCaller
    AUTH_METHOD = Web Connection
    AUTH_NAMED_CONNECTION = @Value(_authentication)
    CONNECTION_TIMEOUT_LENGTH = 60
    ERROR_ATTR = _error
    FOLLOW_REDIRECTS = FOLLOW_WITH_ORIGINAL_METHOD
    HTTP_METHOD = POST
    MULTIPARTS = data StringUpload SOURCE_EXPRESSION;{"EntityType":"@Value(_entity_type)","WOTemplateId":"@Value(_wo_template_id)",@Value(_request_params)};MIME_TYPE;application/json;FME_CONTROLLER_QUERY_FILE;transformers/dependencies/http/StringUpload.fme;FME_CONTROLLER_CHOICE;StringUpload
    REDIRECT_AUTH = ORIGINAL_DOMAIN_ONLY
    SAVE_FILE = Attribute
    STATUS_CODE_ATTR = _http_status_code
    TARGET_ATTR = _response_body
    TARGET_ATTR_ENCODING = auto-detect
    TARGET_URL = @Value(_instance)/Services/AMS/WorkOrder/Create?
    TRANSFER_TIMEOUT_LENGTH = 90
    UPLOAD_TYPE = Multipart / Form Data
    USE_COOKIES = No
    VERIFY_SSL_CERTIFICATES = Yes
    -> JSONExtractor
    <REJECTED> -> <Rejected> (output)
JSONExtractor
    EXTRACT_QUERY_TABLE = _work_order_id json["Value"][0]["WorkOrderId"] _address json["Value"][0]["WOAddress"]
    JSON_DOCUMENT = @Value(_response_body)
    READ_FROM_FILE = NO
    EVALUATED -> AttributeManager
AttributeManager
    ATTR_TABLE = REMOVE _http_status_code
    -> Output (output)

FME custom transformer WorkOrderAttachmentAdder
Description
This transformer leverages the Cityworks REST API to add attachments to existing work orders within Cityworks from FME. It is designed to be used with an authenticated web connection to Cityworks.
Details
The transformer is designed to require only the essential parameters to add an attachment to a work order in Cityworks. An HTTPCaller is used to make the POST call to the Cityworks API, followed by a JSONExtractor to extract valuable information from the response. 
Further configuration of the JSONExtractor can allow you to pull out more attributes from the response based on your custom needs. Similarly, additional parameters can be provided in the Additional Request Parameters field to send a more detailed request to Cityworks.
The Cityworks API allows for all file types to be added to a work order. The API does not allow multiple files to be uploaded at once, so you must select a single file.
Input Ports
Features entering this port trigger the creation of one attachment on an existing work order. Incoming attribute values may be used as input if they are valid parameters of the request URL. If this transformer is intended to be used on its own, a Creator transformer should be used as input to trigger the call without having to read in data.
Output Ports
The outgoing feature carries a _attachment_id attribute, which is the ID of the attachment created in Cityworks. _attachment_location indicates where the attached file has been saved in your Cityworks instance. Further attributes can be output by configuring the JSONExtractor inside the transformer to parse the response from Cityworks. 
There is also a rejected output port that is connected to the HTTPCaller. Further transformers can be connected to the rejected output from inside the custom transformer. Simply create connections between the transformers and the input of the rejected port.
Parameters
Web Connection: The name of your Cityworks web connection.
Cityworks Instance: The path to your Cityworks instance endpoint.
Example: http://localhost/Cityworks
Work Order ID: This parameter is required by all work order add attachment calls to the Cityworks API. An existing work order ID is required in order to know where to upload the attachment.
Attachment: A file path accessible to FME is required to attach a file to an exising work order.
Consult your Cityworks documentation for more request parameters.

Parameters:
- _authentication =   # Cityworks Web Connection
- _instance =   # Cityworks Instance
- _workorderid =   # Work Order ID
- _attachment =   # "" Attachment

Input (input)
    -> ParameterFetcher
ParameterFetcher
    ATTR_LIST = __attachment $(_attachment) __instance $(_instance) __woid $(_workorderid) __authentication $(_authentication)
    -> AddAttachment
Output (output)
Rejected (output)

Bookmark: Add attachment to existing Work Order and clean up output attributes
AddAttachment: HTTPCaller
    ADDITIONAL_URL_PARAMETERS = data;{"WorkOrderId":@Value(__woid)}
    AUTH_METHOD = Web Connection
    AUTH_NAMED_CONNECTION = @Value(__authentication)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    MULTIPARTS = File FileUpload SOURCE_FILE;@Value(__attachment);MIME_TYPE;image/jpeg;FME_CONTROLLER_QUERY_FILE;transformers/dependencies/http/FileUpload.fme;FME_CONTROLLER_CHOICE;FileUpload
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(__instance)/services/Ams/Attachments/AddWorkOrderAttachment?
    TRANSFER_TIMEOUT_LENGTH = 90
    UPLOAD_TYPE = Multipart / Form Data
    USE_COOKIES = No
    VERIFY_SSL_CERTIFICATES = Yes
    -> JSONExtractor
    <REJECTED> -> Rejected (output)
JSONExtractor
    EXTRACT_QUERY_TABLE = _attachment_location json["Value"]["Attachment"] _attachment_id json["Value"]["Id"]
    JSON_DOCUMENT = @Value(_response_body)
    READ_FROM_FILE = NO
    EVALUATED -> AttributeManager
AttributeManager
    ATTR_TABLE:
      REMOVE __attachment
      REMOVE _http_status_code
    USER_EXPOSED_ATTRIBUTES = _attachment_locat,_id
    -> Output (output)
