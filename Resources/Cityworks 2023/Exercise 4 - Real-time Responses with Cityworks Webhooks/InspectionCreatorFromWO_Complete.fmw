FME workspace InspectionCreatorFromWO_Complete.fmw

Parameters:
- webhook = {"WorkOrderId":"294", "Comments":"By%20cwadmin%2C%20cwadmin%20%3A%208%2F1%2F2023%204%3A50%3A20%20PM%20Testing%20my%20FME%20Flow%20workflow", "ApplyToEntity": "DMANHOLE"}   # Webhook Message

Writers:
- AUTOMATIONS_1: AUTOMATIONS to <Unused>

Note: To use this workspace, please update the following. / 1. InspectionCreatorFromWo / - Use your Cityworks Web Connection / - Replace your Cityworks Instance Public IP / 2. User Parameters / Copy the sample webhook message received by your FME Flow Automation. Paste it as the default "webhook" parameter value.
Creator
    GEOMTYPE = Geometry Object
    NUM = 1
    CREATED -> ParameterFetcher
ParameterFetcher
    ATTR_LIST = _webhook $(webhook)
    -> TextDecoder
TextDecoder
    DEST_ATTR = _webhook
    ENCODING_TYPE = URL (Percent Encoding)
    STRING_TO_DECODE = @Value(_webhook)
    -> JSONFlattener
JSONFlattener
    ERROR_LIST_ATTR = _json_error
    JSON_DOCUMENT = @Value(_webhook)
    NEW_ATTRIBUTES = WorkOrderId ApplyToEntity Comments
    READ_FROM_FILE = NO
    RECURSIVE = Yes
    -> InspectionCreatorFromWO
Note: InspectionCreatorFromWO [InspectionCreatorFromWO] / [Embedded] / User Parameters: / Web Connection: administrator Cityworks / Cityworks Instance: http://35.80.38.15/cityworks / Entity Type: @Value(ApplyToEntity) / Inspection Template ID: 2 / Work Order ID: @Value(WorkOrderId) / Additional Request Parameters: <not set>
InspectionCreatorFromWO
    _authentication = administrator Cityworks
    _entity_type = @Value(ApplyToEntity)
    _insp_template_id = 2
    _instance = http://35.80.38.15/cityworks
    _work_order_id = @Value(WorkOrderId)
    -> WorkOrderInspections (writer AUTOMATIONS_1)
WorkOrderInspections (writer AUTOMATIONS_1)
    attributes: _creation_instance string, _webhook string, WorkOrderId string, ApplyToEntity string, Comments string, _work_order_id string, _entity_type string, _instance string, _authentication string, _insp_template_id string, _request_params string, _response_body string, _inspection_id string

FME custom transformer InspectionCreatorFromWO
Description
This transformer leverages the Cityworks REST API to create inspections linked to existing work orders within Cityworks from FME. It is designed to be used with the WorkOrderCreator as input.
Details
The transformer utilizes an HTTPCaller to make the call to the Cityworks API, followed by a JSONExtractor to extract valuable information from the response. Further configuration of the JSONExtractor can allow you to pull out more attributes from the response based on your custom needs. Similarly, additional parameters can be provided in the Additional Request Parameters field to send a more detailed request to Cityworks.
The User Parameter for_entity_type may need configuration to reflect the specific entities of your Cityworks instance.
Input Ports  
Features entering this port trigger the creation of one inspection linked to an existing work order. This transformer will work best when the WorkOrderCreator is used as input. If this transformer is intended to be used on its own, a Creator transformer should be used as input to trigger the call without having to read in data.
Output Ports  
The outgoing feature carries an _inspection_id attribute, which is the ID created in Cityworks along with a _work_order_id attribute which indicates the work order ID it is linked to. Outgoing attributes include all input parameters plus the JSON response body and inspection ID. Further attributes can be output by configuring the JSONExtractor inside the transformer to parse the response from Cityworks.
Parameters
Web Connection: The name of your Cityworks web connection. If there is no input attribute containing a Web Connection, configure the User Parameter to add your own.
Cityworks Instance: The path to your Cityworks instance endpoint.
Example: http://localhost/Cityworks
Entity Type: This parameter is required for successful execution of an inspection linked to an existing work order. It relates to the issue being inspected. Example: Streets or Pavement
Work Order ID: This parameter is required for successful execution of an inspection linked to an existing work order. It is the work order ID that your inspection will link to in Cityworks.
Inspection Template ID: This parameter is required for successful execution of an inspection linked to an existing work order. It will create the inspection with a specific template of questions relating to the Entity Type.
Additional Request Parameters: This parameter can contain one or more extra request parameter definitions which will be included in your inspection. Parameters must be valid for your Cityworks instance. Additional parameters should be formatted with double quotation marks (") surrounding each key and value, with a colon (:) between keys and values. Each key-value pair should be separated by a comma (,).
Example: ''Address'':''1234 Fake St.'',''City'':''NowhereVille''
Consult your Cityworks documentation for more request parameters.

Parameters:
- _authentication =   # Web Connection
- _instance =   # Cityworks Instance
- _entity_type =   # Entity Type
- _insp_template_id =   # "" Inspection Template ID
- _work_order_id =   # Work Order ID
- _request_params =   # Additional Request Parameters

Input (input)
    -> ParameterFetcher
ParameterFetcher
    ATTR_LIST = _insp_template_id $(_insp_template_id) _work_order_id $(_work_order_id) _request_params $(_request_params)
    -> HTTPCaller
HTTPCaller
    AUTH_METHOD = Web Connection
    AUTH_NAMED_CONNECTION = @Value(_authentication)
    CONNECTION_TIMEOUT_LENGTH = 60
    ERROR_ATTR = _error
    FOLLOW_REDIRECTS = Yes
    HTTP_METHOD = POST
    MULTIPARTS = data StringUpload SOURCE_EXPRESSION;{"EntityType":"@Value(_entity_type)","InspTemplateId":"@Value(_insp_template_id)","WorkOrderId":"@Value(_work_order_id)",@Value(_request_params)};MIME_TYPE;application/json;FME_CONTROLLER_QUERY_FILE;transformers/dependencies/http/StringUpload.fme;FME_CONTROLLER_CHOICE;StringUpload
    SAVE_FILE = Attribute
    STATUS_CODE_ATTR = _http_status_code
    TARGET_ATTR = _response_body
    TARGET_ATTR_ENCODING = auto-detect
    TARGET_URL = @Value(_instance)/services/Ams/Inspection/CreateFromWorkOrder?
    TRANSFER_TIMEOUT_LENGTH = 90
    UPLOAD_TYPE = Multipart / Form Data
    USE_COOKIES = No
    VERIFY_SSL_CERTIFICATES = Yes
    -> JSONExtractor
    <REJECTED> -> Terminator
JSONExtractor
    EXTRACT_QUERY_TABLE = _inspection_id json["Value"]["InspectionId"]
    JSON_DOCUMENT = @Value(_response_body)
    READ_FROM_FILE = NO
    EVALUATED -> Output (output)
    <REJECTED> -> Terminator_2
Output (output)
Terminator_2
    MESSAGE = Failed to read JSON response: @Value(fme_rejection_code)
Terminator
    MESSAGE = Malformed call or service not available: @Value(_error)
