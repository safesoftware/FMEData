FME workspace publish-your-validation-workflow.fmw

Parameters:
- SourceDataset_ACAD = c:\FMEData\Resources\DigitalPlanSubmission\bad_data.dwg   # Source Autodesk AutoCAD DWG/DXF File(s)
- DestDataset_HTML = c:\FMEData\Output\Training\validation.html   # Destination Html File

Readers:
- ACAD_1: ACAD from $(SourceDataset_ACAD) in EPSG:2277

Writers:
- HTML_1: HTML to $(DestDataset_HTML)

Bookmark: Read AutoCAD DWG
water_distribution_lines (reader ACAD_1)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
    -> GeometryFilter

Bookmark: Validate Features
Note: Must be a line
GeometryFilter
    BREAK_AGG = No
    GEOM_PORT_NAMES = Line
    LINE -> StatisticsCalculator
Note: Get total feature count
StatisticsCalculator
    CALCULATION_MODE = NUMERIC
    FEAT_STATS = FEATURE_ID,NUMERIC_MODE,,,COUNT,,,,,,,,,
    COMPLETE -> GeometryValidator
Note: Must be OGC valid
GeometryValidator
    ISSUE_ATTR_NAME = _issues
    PRESETS = Custom
    REPAIR = Yes
    RULES = OGC_SIMPLE_CHECK  OGC_VALID_CHECK OGC_VERSION]V1.2.0]FME_CONTROLLER_QUERY_FILE]transformers/dependencies/geometryvalidator/OGC_VALID_CHECK.fme
    SUMMARY = Detailed
    PASSED -> AttributeManager
    FAILED -> AttributeManager
Note: Validate diameter attribute and create summary attributes for validation state
AttributeManager
    ATTR_TABLE:
      SET_TO diam_passed = FME_CONDITIONAL:DEFAULT_VALUE'Invalid'BOOL_OP;OR;COMPOSITE_TEST;1;TEST @Value(DIAMETER) > 0'Valid'FME_NUM_CONDITIONS2___
      SET_TO ogc_passed = FME_CONDITIONAL:DEFAULT_VALUE'Valid'BOOL_OP;OR;COMPOSITE_TEST;1;TEST _issues{0}.count ATTRIBUTE_HAS_A_VALUE _FME_BLANK_STRING_'Invalid'FME_NUM_CONDITIONS2___
      SET_TO validation_result = FME_CONDITIONAL:DEFAULT_VALUE'Valid'BOOL_OP;OR;COMPOSITE_TEST;1 OR 2;TEST @Value(diam_passed) = Invalid;TEST @Value(ogc_passed) = Invalid'Invalid'FME_NUM_CONDITIONS2___
      RENAME_SET_VALUE FEATURE_ID.total_count > total_features
    -> StatisticsCalculator_2
Note: Get total invalid feature count
StatisticsCalculator_2
    CALCULATION_MODE = NUMERIC
    FEAT_STATS = FEATURE_ID,NUMERIC_MODE,,,COUNT,,,,,,,,,;total_features,NUMERIC_MODE,,MAX,,,,,,,,,,
    GROUP_BY = validation_result
    SUMMARY -> DateTimeStamper
    COMPLETE -> Tester
Note: Filter data by valid and invalid features
Tester
    BOOL_OP = OR
    COMPOSITE_TEST = 1
    TEST_CLAUSE = TEST @Value(validation_result) = Valid
    TEST_MODE = TEST
    FAILED -> AttributeCreator
    FAILED -> HTMLReportGenerator_3

Bookmark: Create a summary section
Note: Create current date attribute
DateTimeStamper
    DATETIME_ATTR = _timestamp
    INCLUDE_OFFSET = NO
    STAMP_TYPE = datetime
    TIMEZONE = local
    -> HTMLReportGenerator
Note: Create header and report of total valid/invalid features
HTMLReportGenerator
    CONTENT_LIST = HEADER HTML TABLE
    PAGE_CONFIG:
      HEADER{{TEXT;Data Validation Report;HEADER;H1;HEADER_ID;;ALIGNMENT;LEFT;COLOR;0,0,0;FME_CONTROLLER_QUERY_FILE;transformers/dependencies/html5/Header.fme}}HTML{{HTML;<p>Report Date: @DateTimeFormat(@Value(_timestamp),%Y-%m-%d %H:%M)</p>
      <p>Total Features: @Value(total_features.max)</p>;FME_CONTROLLER_QUERY_FILE;transformers/dependencies/html5/Custom HTML.fme}}TABLE{{STYLE;STRIPED;TABLE;validation_result|Validation Result/FEATURE_ID.total_count|Features;FME_CONTROLLER_QUERY_FILE;transformers/dependencies/html5/Table.fme}}
    -> AttributeCreator_2
Note: Set HTML section write order (0)
AttributeCreator_2
    ATTR_TABLE = SET_TO order = 0
    -> Sorter

Bookmark: Create a web map of invalid features
Note: Create map label
AttributeCreator
    ATTR_TABLE = SET_TO label = ID: @Value(FEATURE_ID). OGC valid: @Value(ogc_passed). Diameter valid: @Value(diam_passed).
    -> HTMLReportGenerator_2
Note: Create map of invalid features
HTMLReportGenerator_2
    CONTENT_LIST = HEADER MAP_ESRI
    PAGE_CONFIG = HEADER{{TEXT;Invalid Features Map;HEADER;H1;HEADER_ID;;ALIGNMENT;LEFT;COLOR;0,0,0;FME_CONTROLLER_QUERY_FILE;transformers/dependencies/html5/Header.fme}}MAP_ESRI{{LABEL;label;COLOR;0,0,255;BASEMAP;Streets;URLS;;FME_CONTROLLER_QUERY_FILE;transformers/dependencies/html5/Map (Esri Leaflet).fme}}
    -> AttributeCreator_3
Note: Set HTML section write order (1)
AttributeCreator_3
    ATTR_TABLE = SET_TO order = 1
    -> Sorter

Bookmark: Create an HTML table of invalid features
Note: Create a table of invalid features
HTMLReportGenerator_3
    CONTENT_LIST = HEADER TABLE
    PAGE_CONFIG = HEADER{{TEXT;Invalid Features Table;HEADER;H1;HEADER_ID;;ALIGNMENT;LEFT;COLOR;0,0,0;FME_CONTROLLER_QUERY_FILE;transformers/dependencies/html5/Header.fme}}TABLE{{STYLE;STRIPED;TABLE;FEATURE_ID|Feature ID/ogc_passed|OGC Valid?/diam_passed|Diameter Valid?;FME_CONTROLLER_QUERY_FILE;transformers/dependencies/html5/Table.fme}}
    -> AttributeCreator_4
Note: Set HTML section write order (2)
AttributeCreator_4
    ATTR_TABLE = SET_TO order = 2
    -> Sorter

Bookmark: Layout HTML report
Note: Sort HTML sections
Sorter
    SORT_PARM = order NUMERIC ASCENDING
    SORTED -> HTMLLayouter
Note: Add margins and page title
HTMLLayouter
    DIV_STYLE = NONE
    LAYOUT = VERTICAL
    TITLE = Validation Results
    -> HTML (writer HTML_1)
Note: Write HTML report
HTML (writer HTML_1)
    attributes: html_content buffer
