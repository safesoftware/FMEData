FME workspace UseAIToSelectMCPTools-complete.fmw

Parameters:
- USER_REQUEST = Get the current weather forecast for Vancouver   # Prompt to Weather MCP Server

AttributeCreator
    ATTR_TABLE:
      SET_TO user_request (varchar(200)) = $(USER_REQUEST)
      SET_TO today (varchar(200)) = @DateTimeFormat(@CurrentDateTime(),%Y-%m-%d)
      SET_TO all_mcp_tools (varchar(200)) = @Value(_json_response)
    INPUT_PORT_CONNECTED = CONNECTED
    SHOW_ERROR_INDICATORS = No
    -> OpenAIConnector
OpenAIConnector
    INPUT_PORT_CONNECTED = CONNECTED
    SHOW_ERROR_INDICATORS = No
    ___XF_ACCOUNT = Training OpenAI (safe.openai)
    ___XF_CONVERSATION_STATE = NONE
    ___XF_INCLUDE_RESPONSE_JSON = yes
    ___XF_INPUT_TEXT:
      You are selecting a weather MCP tool based on a user request.

      Available tools, including descriptions and input schemas:
      @Value(all_mcp_tools)

      User request:
      @Value(user_request)

      Your task:
      Select the most appropriate weather tool and construct the tool_input that matches the selected tool's input schema exactly.

      Rules:
      - You MUST select tool_name exactly from the provided tool list.
      - You MUST provide a tool_input that matches the input schema of the selected tool.
      - Do not rename tools or invent new ones.
      - Vancouver coordinates are latitude: 49.2827, longitude: -123.1207, timezone: "America/Vancouver".
      - Use these coordinates for any location-based tool unless the user specifies a different location.
      - If you do not know the geographic coordinates from the place name from the user request, estimate the coordinates from your knowledge to format the tool input.
      - For weather_archive, today's date is @Value(today) — use a reasonable past date range.
      - Do not use the geocoding tool.


      Schema rules:
      - tool_input must strictly follow the input schema of the selected tool.
      - Preserve object structure and nesting exactly.
      - Include all required fields.
      - Do not add fields not defined in the schema.
    ___XF_JSON_SCHEMA:
      {
        "type": "object",
        "properties": {
          "tool_name": {
            "type": "string"
          },
          "tool_input": {
            "type": "object",
            "additionalProperties": true
          }
        },
        "required": ["tool_name", "tool_input"],
        "additionalProperties": false
      }
    ___XF_MODEL = chat-latest
    ___XF_REQUEST_ACTION = RESPONSE_CREATE
    ___XF_SCHEMA_NAME = tool_selection
    ___XF_TIMEOUT = 120
    ___XF_WEB_SEARCH = NO
    -> JSONFlattener
JSONFlattener
    ERROR_LIST_ATTR = _json_error
    INPUT_PORT_CONNECTED = CONNECTED
    JSON_DOCUMENT = @Value(_output_text)
    NEW_ATTRIBUTES = tool_name buffer tool_input buffer
    READ_FROM_FILE = NO
    RECURSIVE = NO
    SHOW_ERROR_INDICATORS = No

Bookmark: List Tools
MCPCaller
    INPUT_PORT_CONNECTED = *
    SHOW_ERROR_INDICATORS = No
    ___XF_AUTH_METHOD = NONE
    ___XF_INCLUDE_RESPONSE_JSON = YES
    ___XF_MCP_METHOD = LIST_TOOLS
    ___XF_OUTPUT_GROUPING = SINGLE_FEATURE_WITH_LIST
    ___XF_SERVER_URL = http://weather-mcp:3000/mcp
    ___XF_TIMEOUT = 30
    -> AttributeCreator

Bookmark: Call Tool
MCPCaller_2
    INPUT_PORT_CONNECTED = *
    SHOW_ERROR_INDICATORS = No
    ___XF_AUTH_METHOD = NONE
    ___XF_INCLUDE_RESPONSE_JSON = YES
    ___XF_INPUT_SCHEMA_PREVIEW:
      {
          "properties": {
              "current": {
                  "description": "Current conditions variables to retrieve. Preferred over the deprecated current_weather boolean.",
                  "items": {
                      "enum": [
                          "temperature_2m",
                          "relative_humidity_2m",
                          "dewpoint_2m",
                          "apparent_temperature",
                          "precipitation_probability",
                          "precipitation",
                          "rain",
                          "showers",
                          "snowfall",
                          "snow_depth",
                          "weather_code",
                          "pressure_msl",
                          "surface_pressure",
                          "cloud_cover",
                          "cloud_cover_low",
                          "cloud_cover_mid",
                          "cloud_cover_high",
                          "visibility",
                          "evapotranspiration",
                          "et0_fao_evapotranspiration",
                          "vapour_pressure_deficit",
                          "wind_speed_10m",
                          "wind_speed_80m",
                          "wind_speed_120m",
                          "wind_speed_180m",
                          "wind_direction_10m",
                          "wind_direction_80m",
                          "wind_direction_120m",
                          "wind_direction_180m",
                          "wind_gusts_10m",
                          "temperature_80m",
                          "temperature_120m",
                          "temperature_180m",
                          "soil_temperature_0cm",
                          "soil_temperature_6cm",
                          "soil_temperature_18cm",
                          "soil_temperature_54cm",
                          "soil_moisture_0_to_1cm",
                          "soil_moisture_1_to_3cm",
                          "soil_moisture_3_to_9cm",
                          "soil_moisture_9_to_27cm",
                          "soil_moisture_27_to_81cm",
                          "uv_index",
                          "uv_index_clear_sky",
                          "is_day",
                          "sunshine_duration",
                          "wet_bulb_temperature_2m",
                          "total_column_integrated_water_vapour",
                          "cape",
                          "lifted_index",
                          "convective_inhibition",
                          "freezing_level_height",
                          "boundary_layer_height_pbl",
                          "shortwave_radiation",
                          "direct_radiation",
                          "diffuse_radiation",
                          "direct_normal_irradiance",
                          "global_tilted_irradiance",
                          "terrestrial_radiation",
                          "shortwave_radiation_instant",
                          "direct_radiation_instant",
                          "diffuse_radiation_instant",
                          "direct_normal_irradiance_instant",
                          "global_tilted_irradiance_instant",
                          "terrestrial_radiation_instant"
                      ],
                      "type": "string"
                  },
                  "type": "array"
              },
              "current_weather": {
                  "description": "Include current weather conditions",
                  "type": "boolean"
              },
              "daily": {
                  "description": "Daily weather variables to retrieve",
                  "items": {
                      "enum": [
                          "weather_code",
                          "temperature_2m_max",
                          "temperature_2m_min",
                          "apparent_temperature_max",
                          "apparent_temperature_min",
                          "sunrise",
                          "sunset",
                          "daylight_duration",
                          "sunshine_duration",
                          "uv_index_max",
                          "uv_index_clear_sky_max",
                          "rain_sum",
                          "showers_sum",
                          "snowfall_sum",
                          "precipitation_sum",
                          "precipitation_hours",
                          "precipitation_probability_max",
                          "wind_speed_10m_max",
                          "wind_gusts_10m_max",
                          "wind_direction_10m_dominant",
                          "shortwave_radiation_sum",
                          "et0_fao_evapotranspiration",
                          "temperature_2m_mean",
                          "apparent_temperature_mean",
                          "cape_mean",
                          "cape_max",
                          "cape_min",
                          "cloud_cover_mean",
                          "cloud_cover_max",
                          "cloud_cover_min",
                          "dewpoint_2m_mean",
                          "dewpoint_2m_max",
                          "dewpoint_2m_min",
                          "et0_fao_evapotranspiration_sum",
                          "growing_degree_days_base_0_limit_50",
                          "leaf_wetness_probability_mean",
                          "leaf_wetness_probability_max",
                          "leaf_wetness_probability_min",
                          "precipitation_probability_mean",
                          "precipitation_probability_min",
                          "relative_humidity_2m_mean",
                          "relative_humidity_2m_max",
                          "relative_humidity_2m_min",
                          "snowfall_water_equivalent_sum",
                          "pressure_msl_mean",
                          "pressure_msl_max",
                          "pressure_msl_min",
                          "surface_pressure_mean",
                          "surface_pressure_max",
                          "surface_pressure_min",
                          "updraft_max",
                          "visibility_mean",
                          "visibility_max",
                          "visibility_min",
                          "wind_gusts_10m_mean",
                          "wind_gusts_10m_min",
                          "wind_speed_10m_mean",
                          "wind_speed_10m_min",
                          "wet_bulb_temperature_2m_mean",
                          "wet_bulb_temperature_2m_max",
                          "wet_bulb_temperature_2m_min",
                          "vapour_pressure_deficit_max"
                      ],
                      "type": "string"
                  },
                  "type": "array"
              },
              "forecast_days": {
                  "default": 7,
                  "description": "Number of forecast days",
                  "maximum": 16,
                  "minimum": 1,
                  "type": "integer"
              },
              "hourly": {
                  "description": "Hourly weather variables to retrieve",
                  "items": {
                      "enum": [
                          "temperature_2m",
                          "relative_humidity_2m",
                          "dewpoint_2m",
                          "apparent_temperature",
                          "precipitation_probability",
                          "precipitation",
                          "rain",
                          "showers",
                          "snowfall",
                          "snow_depth",
                          "weather_code",
                          "pressure_msl",
                          "surface_pressure",
                          "cloud_cover",
                          "cloud_cover_low",
                          "cloud_cover_mid",
                          "cloud_cover_high",
                          "visibility",
                          "evapotranspiration",
                          "et0_fao_evapotranspiration",
                          "vapour_pressure_deficit",
                          "wind_speed_10m",
                          "wind_speed_80m",
                          "wind_speed_120m",
                          "wind_speed_180m",
                          "wind_direction_10m",
                          "wind_direction_80m",
                          "wind_direction_120m",
                          "wind_direction_180m",
                          "wind_gusts_10m",
                          "temperature_80m",
                          "temperature_120m",
                          "temperature_180m",
                          "soil_temperature_0cm",
                          "soil_temperature_6cm",
                          "soil_temperature_18cm",
                          "soil_temperature_54cm",
                          "soil_moisture_0_to_1cm",
                          "soil_moisture_1_to_3cm",
                          "soil_moisture_3_to_9cm",
                          "soil_moisture_9_to_27cm",
                          "soil_moisture_27_to_81cm",
                          "uv_index",
                          "uv_index_clear_sky",
                          "is_day",
                          "sunshine_duration",
                          "wet_bulb_temperature_2m",
                          "total_column_integrated_water_vapour",
                          "cape",
                          "lifted_index",
                          "convective_inhibition",
                          "freezing_level_height",
                          "boundary_layer_height_pbl",
                          "shortwave_radiation",
                          "direct_radiation",
                          "diffuse_radiation",
                          "direct_normal_irradiance",
                          "global_tilted_irradiance",
                          "terrestrial_radiation",
                          "shortwave_radiation_instant",
                          "direct_radiation_instant",
                          "diffuse_radiation_instant",
                          "direct_normal_irradiance_instant",
                          "global_tilted_irradiance_instant",
                          "terrestrial_radiation_instant"
                      ],
                      "type": "string"
                  },
                  "type": "array"
              },
              "latitude": {
                  "description": "Latitude in WGS84 coordinate system",
                  "maximum": 90,
                  "minimum": -90,
                  "type": "number"
              },
              "longitude": {
                  "description": "Longitude in WGS84 coordinate system",
                  "maximum": 180,
                  "minimum": -180,
                  "type": "number"
              },
              "models": {
                  "description": "Weather model to use. Only one model per request — multi-value arrays are not supported by the API. Omit this parameter to let the API automatically select the best model for the location (recommended). For multi-model comparison, make one parallel tool call per model using the appropriate provider-specific tool.",
                  "enum": [
                      "ecmwf_ifs04",
                      "ecmwf_ifs025",
                      "ecmwf_aifs025_single",
                      "cma_grapes_global",
                      "bom_access_global",
                      "gfs_seamless",
                      "ncep_gfs_global",
                      "ncep_hrrr_conus",
                      "ncep_nbm_conus",
                      "ncep_nam_conus",
                      "ncep_gfs_graphcast025",
                      "ncep_aigfs025",
                      "ncep_hgefs025_ensemble_mean",
                      "jma_seamless",
                      "jma_msm",
                      "jma_gsm",
                      "kma_seamless",
                      "kma_ldps",
                      "kma_gdps",
                      "dwd_icon_seamless",
                      "dwd_icon_global",
                      "dwd_icon_eu",
                      "dwd_icon_d2",
                      "gem_seamless",
                      "gem_global",
                      "gem_regional",
                      "gem_hrdps_continental",
                      "gem_hrdps_west",
                      "meteofrance_seamless",
                      "meteofrance_arpege_world",
                      "meteofrance_arpege_europe",
                      "meteofrance_arome_france",
                      "meteofrance_arome_france_hd",
                      "italia_meteo_arpae_icon_2i",
                      "metno_seamless",
                      "metno_nordic",
                      "knmi_seamless",
                      "knmi_harmonie_arome_europe",
                      "knmi_harmonie_arome_netherlands",
                      "dmi_seamless",
                      "dmi_harmonie_arome_europe",
                      "ukmo_seamless",
                      "ukmo_global_deterministic_10km",
                      "ukmo_uk_deterministic_2km",
                      "meteoswiss_icon_seamless",
                      "meteoswiss_icon_ch1",
                      "meteoswiss_icon_ch2"
                  ],
                  "type": "string"
              },
              "past_days": {
                  "description": "Include past days data (1–92)",
                  "maximum": 92,
                  "minimum": 1,
                  "type": "integer"
              },
              "precipitation_unit": {
                  "default": "mm",
                  "description": "Precipitation unit",
                  "enum": [
                      "mm",
                      "inch"
                  ],
                  "type": "string"
              },
              "temperature_unit": {
                  "default": "celsius",
                  "description": "Temperature unit",
                  "enum": [
                      "celsius",
                      "fahrenheit"
                  ],
                  "type": "string"
              },
              "timezone": {
                  "description": "Timezone for timestamps (e.g., Europe/Paris, America/New_York)",
                  "type": "string"
              },
              "wind_speed_unit": {
                  "default": "kmh",
                  "description": "Wind speed unit",
                  "enum": [
                      "kmh",
                      "ms",
                      "mph",
                      "kn"
                  ],
                  "type": "string"
              }
          },
          "required": [
              "latitude",
              "longitude"
          ],
          "type": "object"
      }
    ___XF_JSON_TEXT:
      {
      	"current_weather": true,
      	"forecast_days": 7,
      	"latitude": 49.2827,
      	"longitude": -123.1207,
      	"precipitation_unit": "mm",
      	"temperature_unit": "celsius",
      	"timezone": "America/Vancouver",
      	"wind_speed_unit": "kmh"
      }
    ___XF_MCP_METHOD = CALL_TOOL
    ___XF_SERVER_URL = http://weather-mcp:3000/mcp
    ___XF_TIMEOUT = 30
    ___XF_TOOL = [{"display":"weather_forecast","value":"{\"name\":\"weather_forecast\",\"title\":null,\"description\":\"Get weather forecast data for coordinates using Open-Meteo API. Supports hourly and daily data with various weather variables. When no `models` parameter is provided, the API automatically selects the best model for the given location (recommended). Only one model per request is supported — for multi-model comparison, use provider-specific tools with parallel calls.\",\"inputSchema\":{\"type\":\"object\",\"properties\":{\"latitude\":{\"type\":\"number\",\"minimum\":-90,\"maximum\":90,\"description\":\"Latitude in WGS84 coordinate system\"},\"longitude\":{\"type\":\"number\",\"minimum\":-180,\"maximum\":180,\"description\":\"Longitude in WGS84 coordinate system\"},\"hourly\":{\"type\":\"array\",\"items\":{\"type\":\"string\",\"enum\":[\"temperature_2m\",\"relative_humidity_2m\",\"dewpoint_2m\",\"apparent_temperature\",\"precipitation_probability\",\"precipitation\",\"rain\",\"showers\",\"snowfall\",\"snow_depth\",\"weather_code\",\"pressure_msl\",\"surface_pressure\",\"cloud_cover\",\"cloud_cover_low\",\"cloud_cover_mid\",\"cloud_cover_high\",\"visibility\",\"evapotranspiration\",\"et0_fao_evapotranspiration\",\"vapour_pressure_deficit\",\"wind_speed_10m\",\"wind_speed_80m\",\"wind_speed_120m\",\"wind_speed_180m\",\"wind_direction_10m\",\"wind_direction_80m\",\"wind_direction_120m\",\"wind_direction_180m\",\"wind_gusts_10m\",\"temperature_80m\",\"temperature_120m\",\"temperature_180m\",\"soil_temperature_0cm\",\"soil_temperature_6cm\",\"soil_temperature_18cm\",\"soil_temperature_54cm\",\"soil_moisture_0_to_1cm\",\"soil_moisture_1_to_3cm\",\"soil_moisture_3_to_9cm\",\"soil_moisture_9_to_27cm\",\"soil_moisture_27_to_81cm\",\"uv_index\",\"uv_index_clear_sky\",\"is_day\",\"sunshine_duration\",\"wet_bulb_temperature_2m\",\"total_column_integrated_water_vapour\",\"cape\",\"lifted_index\",\"convective_inhibition\",\"freezing_level_height\",\"boundary_layer_height_pbl\",\"shortwave_radiation\",\"direct_radiation\",\"diffuse_radiation\",\"direct_normal_irradiance\",\"global_tilted_irradiance\",\"terrestrial_radiation\",\"shortwave_radiation_instant\",\"direct_radiation_instant\",\"diffuse_radiation_instant\",\"direct_normal_irradiance_instant\",\"global_tilted_irradiance_instant\",\"terrestrial_radiation_instant\"]},\"description\":\"Hourly weather variables to retrieve\"},\"daily\":{\"type\":\"array\",\"items\":{\"type\":\"string\",\"enum\":[\"weather_code\",\"temperature_2m_max\",\"temperature_2m_min\",\"apparent_temperature_max\",\"apparent_temperature_min\",\"sunrise\",\"sunset\",\"daylight_duration\",\"sunshine_duration\",\"uv_index_max\",\"uv_index_clear_sky_max\",\"rain_sum\",\"showers_sum\",\"snowfall_sum\",\"precipitation_sum\",\"precipitation_hours\",\"precipitation_probability_max\",\"wind_speed_10m_max\",\"wind_gusts_10m_max\",\"wind_direction_10m_dominant\",\"shortwave_radiation_sum\",\"et0_fao_evapotranspiration\",\"temperature_2m_mean\",\"apparent_temperature_mean\",\"cape_mean\",\"cape_max\",\"cape_min\",\"cloud_cover_mean\",\"cloud_cover_max\",\"cloud_cover_min\",\"dewpoint_2m_mean\",\"dewpoint_2m_max\",\"dewpoint_2m_min\",\"et0_fao_evapotranspiration_sum\",\"growing_degree_days_base_0_limit_50\",\"leaf_wetness_probability_mean\",\"leaf_wetness_probability_max\",\"leaf_wetness_probability_min\",\"precipitation_probability_mean\",\"precipitation_probability_min\",\"relative_humidity_2m_mean\",\"relative_humidity_2m_max\",\"relative_humidity_2m_min\",\"snowfall_water_equivalent_sum\",\"pressure_msl_mean\",\"pressure_msl_max\",\"pressure_msl_min\",\"surface_pressure_mean\",\"surface_pressure_max\",\"surface_pressure_min\",\"updraft_max\",\"visibility_mean\",\"visibility_max\",\"visibility_min\",\"wind_gusts_10m_mean\",\"wind_gusts_10m_min\",\"wind_speed_10m_mean\",\"wind_speed_10m_min\",\"wet_bulb_temperature_2m_mean\",\"wet_bulb_temperature_2m_max\",\"wet_bulb_temperature_2m_min\",\"vapour_pressure_deficit_max\"]},\"description\":\"Daily weather variables to retrieve\"},\"current_weather\":{\"type\":\"boolean\",\"description\":\"Include current weather conditions\"},\"current\":{\"type\":\"array\",\"items\":{\"type\":\"string\",\"enum\":[\"temperature_2m\",\"relative_humidity_2m\",\"dewpoint_2m\",\"apparent_temperature\",\"precipitation_probability\",\"precipitation\",\"rain\",\"showers\",\"snowfall\",\"snow_depth\",\"weather_code\",\"pressure_msl\",\"surface_pressure\",\"cloud_cover\",\"cloud_cover_low\",\"cloud_cover_mid\",\"cloud_cover_high\",\"visibility\",\"evapotranspiration\",\"et0_fao_evapotranspiration\",\"vapour_pressure_deficit\",\"wind_speed_10m\",\"wind_speed_80m\",\"wind_speed_120m\",\"wind_speed_180m\",\"wind_direction_10m\",\"wind_direction_80m\",\"wind_direction_120m\",\"wind_direction_180m\",\"wind_gusts_10m\",\"temperature_80m\",\"temperature_120m\",\"temperature_180m\",\"soil_temperature_0cm\",\"soil_temperature_6cm\",\"soil_temperature_18cm\",\"soil_temperature_54cm\",\"soil_moisture_0_to_1cm\",\"soil_moisture_1_to_3cm\",\"soil_moisture_3_to_9cm\",\"soil_moisture_9_to_27cm\",\"soil_moisture_27_to_81cm\",\"uv_index\",\"uv_index_clear_sky\",\"is_day\",\"sunshine_duration\",\"wet_bulb_temperature_2m\",\"total_column_integrated_water_vapour\",\"cape\",\"lifted_index\",\"convective_inhibition\",\"freezing_level_height\",\"boundary_layer_height_pbl\",\"shortwave_radiation\",\"direct_radiation\",\"diffuse_radiation\",\"direct_normal_irradiance\",\"global_tilted_irradiance\",\"terrestrial_radiation\",\"shortwave_radiation_instant\",\"direct_radiation_instant\",\"diffuse_radiation_instant\",\"direct_normal_irradiance_instant\",\"global_tilted_irradiance_instant\",\"terrestrial_radiation_instant\"]},\"description\":\"Current conditions variables to retrieve. Preferred over the deprecated current_weather boolean.\"},\"temperature_unit\":{\"type\":\"string\",\"enum\":[\"celsius\",\"fahrenheit\"],\"default\":\"celsius\",\"description\":\"Temperature unit\"},\"wind_speed_unit\":{\"type\":\"string\",\"enum\":[\"kmh\",\"ms\",\"mph\",\"kn\"],\"default\":\"kmh\",\"description\":\"Wind speed unit\"},\"precipitation_unit\":{\"type\":\"string\",\"enum\":[\"mm\",\"inch\"],\"default\":\"mm\",\"description\":\"Precipitation unit\"},\"timezone\":{\"type\":\"string\",\"description\":\"Timezone for timestamps (e.g., Europe/Paris, America/New_York)\"},\"past_days\":{\"type\":\"integer\",\"minimum\":1,\"maximum\":92,\"description\":\"Include past days data (1–92)\"},\"forecast_days\":{\"type\":\"integer\",\"minimum\":1,\"maximum\":16,\"default\":7,\"description\":\"Number of forecast days\"},\"models\":{\"type\":\"string\",\"enum\":[\"ecmwf_ifs04\",\"ecmwf_ifs025\",\"ecmwf_aifs025_single\",\"cma_grapes_global\",\"bom_access_global\",\"gfs_seamless\",\"ncep_gfs_global\",\"ncep_hrrr_conus\",\"ncep_nbm_conus\",\"ncep_nam_conus\",\"ncep_gfs_graphcast025\",\"ncep_aigfs025\",\"ncep_hgefs025_ensemble_mean\",\"jma_seamless\",\"jma_msm\",\"jma_gsm\",\"kma_seamless\",\"kma_ldps\",\"kma_gdps\",\"dwd_icon_seamless\",\"dwd_icon_global\",\"dwd_icon_eu\",\"dwd_icon_d2\",\"gem_seamless\",\"gem_global\",\"gem_regional\",\"gem_hrdps_continental\",\"gem_hrdps_west\",\"meteofrance_seamless\",\"meteofrance_arpege_world\",\"meteofrance_arpege_europe\",\"meteofrance_arome_france\",\"meteofrance_arome_france_hd\",\"italia_meteo_arpae_icon_2i\",\"metno_seamless\",\"metno_nordic\",\"knmi_seamless\",\"knmi_harmonie_arome_europe\",\"knmi_harmonie_arome_netherlands\",\"dmi_seamless\",\"dmi_harmonie_arome_europe\",\"ukmo_seamless\",\"ukmo_global_deterministic_10km\",\"ukmo_uk_deterministic_2km\",\"meteoswiss_icon_seamless\",\"meteoswiss_icon_ch1\",\"meteoswiss_icon_ch2\"],\"description\":\"Weather model to use. Only one model per request — multi-value arrays are not supported by the API. Omit this parameter to let the API automatically select the best model for the location (recommended). For multi-model comparison, make one parallel tool call per model using the appropriate provider-specific tool.\"}},\"required\":[\"latitude\",\"longitude\"]},\"outputSchema\":null,\"icons\":null,\"annotations\":null,\"meta\":null,\"execution\":null}"}]
    ___XF_TOOL_INPUT_SOURCE = TEXT_OR_ATTR
