FME workspace CellSignalByNeighborhood-complete.fmw

Parameters:
- NEIGHBORHOOD = Strathcona   # Pleasant"%Downtown%"West End"%Strathcona Vancouver Neighborhood
- DestDataset_MCP = C:\FMEData\Output   # Destination MCP Folder

Readers:
- OGCKML_1: OGCKML from https://s3.amazonaws.com/FMEData/FMEData/Data/Boundaries/VancouverNeighborhoods.kml
- CSV2_1: CSV2 from https://s3.amazonaws.com/FMEData/FMEData/Data/CellSignals/CellSignal.csv

Writers:
- MCP_1: MCP to $(DestDataset_MCP)

Tester
    BOOL_OP = OR
    SHOW_ERROR_INDICATORS = No
    TEST_CLAUSE = TEST @Value(NeighborhoodName) = $(NEIGHBORHOOD)
    TEST_MODE = TEST
    PASSED -> SpatialFilter [Filter]
SpatialFilter
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = NO
    PREDATTR = _predicate
    PREDICATES = INTERSECTS
    SHOW_ERROR_INDICATORS = No
    PASSED -> StatisticsCalculator
StatisticsCalculator
    ATTR_ACCUM_MODE = None
    CALCULATION_MODE = NUMERIC
    FEAT_STATS = Power,NUMERIC_MODE,MIN,MAX,COUNT,,MEAN,,,,,,,,;Quality,NUMERIC_MODE,MIN,MAX,COUNT,,MEAN,,,,,,,,
    GROUP_BY = NeighborhoodName
    SHOW_ERROR_INDICATORS = No
    SUMMARY -> AttributeCreator
AttributeCreator
    ATTR_TABLE:
      SET_TO text (varchar(200)) = Cell signal quality summary for @Value(NeighborhoodName):
        @Value(Power.total_count) measurements found.
        Average signal power: @Value(Power.mean) (min:@Value(Power.min), max: @Value(Power.max))
        Average signal quality: @Value(Quality.mean) (min: @Value(Quality.min), max: @Value(Quality.max))
    INPUT_PORT_CONNECTED = CONNECTED
    SHOW_ERROR_INDICATORS = No
    -> Text Content (writer MCP_1)
Text Content (writer MCP_1)
    attributes: text string, annotations.audience{} string, annotations.priority float

Bookmark: Read Vancouver Neighborhoods
Neighborhoods (reader OGCKML_1)
    attributes: NeighborhoodId kml_buffer, NeighborhoodName kml_buffer, NeighborhoodURL kml_buffer, TotalPopulation2001 kml_buffer, TotalPopulation2011 kml_buffer
    -> Tester

Bookmark: Read Cell Signal Data
CSV (reader CSV2_1)
    attributes: longitude real64, latitude real64, StationID uint32, Power real64, Quality real32, num_measures uint32, Code varchar(13), recorded_tstamp varchar(20)
    -> SpatialFilter [Candidate]
