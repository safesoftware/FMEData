FME workspace get-geometry-input-NEW-complete.fmw

Parameters:
- GEOM_COORDS = {"type":"Polygon","coordinates":[[[-123.131762,49.282752],[-123.132148,49.282465],[-123.131579,49.282087],[-123.131139,49.282332],[-123.131762,49.282752]]]}   # Select Construction Area
- FORMAT = XLSXW   # GeoPackage,OGCGEOPACKAGE%Esri Shapefile,SHAPEFILE%Microsoft Excel,XLSXW Output format

Writers:
- GENERIC_1: GENERIC to C:\FMEData\Output\Training

Creator
    GEOMTYPE = No Geometry
    NUM = 1
    CREATED -> GeometryReplacer
    CREATED -> FeatureReader [INITIATOR]
Note: Read in address points
FeatureReader
    ATTRS_TO_EXPOSE = COUNTRY GlobalID INTPSTLCD INTSTATE LASTEDITOR LASTUPDATE OBJECTID openfilegdb_type OWNERNM1 OWNERNM2 POSTALCODE PSTLADDRESS PSTLCITY PSTLPROV REPRESENT STATUS
    ATTR_ACCUM_MODE = Only Use Result
    CLIP_TO_ENVELOPE = NO
    COMBINE_GEOM = Use Result
    DATASET = C:\FMEData\Data\Addresses\Addresses.gdb
    FORMAT = OPENFILEGDB
    INITIATOR_FIRST_OUTPUT = default
    INPUT_PORT_INITIATOR_CONNECTED = CONNECTED
    INTERACT = NONE
    OPENFILEGDB_QUERY_FEATURE_TYPES_FOR_MERGE_FILTERS = Yes
    OPENFILEGDB_READ_BOOLEANS_AS_YES_NO = YES
    OPENFILEGDB_READ_NULLS = YES
    OPENFILEGDB_REMOVE_FEATURE_DATASET = NO
    OPENFILEGDB_SIMPLE_DONUT_GEOMETRY = simple
    OPENFILEGDB_STRIP_GUID_GLOBALID_BRACES = no
    OPENFILEGDB_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = SELECTFEATTYPES
    <OTHER> -> Reprojector_2
Reprojector_2
    DEST = UTM83-10
    INTERPOLATION_TYPE = NearestNeighbor
    RASTER_CELL_SIZE = PreserveCells
    RASTER_TOLERANCE = 0.0
    REPROJECTED -> Clipper [CANDIDATE]
Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_PARTS
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeKeeper
AttributeKeeper
    CREATE_BULK_MODE_FEATURES = NO
    KEEP_ATTRS = OWNERNM1,POSTALCODE,PSTLADDRESS,PSTLCITY,PSTLPROV
    -> NotifyList (writer GENERIC_1)
Note: Write an table of affected addresses to Excel, Shapefile, Geopackage, or GeoJSON
NotifyList (writer GENERIC_1)
    attributes: OWNERNM1 buffer, POSTALCODE buffer, PSTLADDRESS buffer, PSTLCITY buffer, PSTLPROV buffer

Bookmark: Create an area of interest polygon and buffer it to 100 m to capture affected addresses
GeometryReplacer
    KIND = GEOJSON
    REMOVE_ATTRIBUTE = Yes
    SOURCE = $(GEOM_COORDS)
    KIND_LONG = GeoJSON
    -> CoordinateSystemSetter
CoordinateSystemSetter
    COORDSYS = LL84
    -> Reprojector
Reprojector
    DEST = UTM83-10
    INTERPOLATION_TYPE = NearestNeighbor
    RASTER_CELL_SIZE = PreserveCells
    RASTER_TOLERANCE = 0.0
    REPROJECTED -> Bufferer
Bufferer
    ANGLE = 22.5
    CAP_STYLE_LOOKUP = CAP_ARC
    CORNER_STYLE_LOOKUP = JOIN_ARC
    MODE = AREA
    OFFSET = 100
    OFFSET_UNITS = METERS
    PRECISION = APPROX
    CAP_STYLE = Arc
    CORNER_STYLE = Arc
    BUFFERED -> Clipper [CLIPPER]
