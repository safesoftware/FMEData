FME workspace deploy-workflows-to-multiple-environments--complete.fmw

Readers:
- POSTGIS_1: POSTGIS from $(TrainingDatabase)

Writers:
- NULL_1: NULL

Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_PARTS
    MISSING_M_MODE_LOOKUP = LINEAR
    MISSING_Z_MODE_LOOKUP = LINEAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Linear Interpolation
    INSIDE -> Schools (writer NULL_1)
Schools (writer NULL_1)
    attributes: NeighborhoodId char(255), NeighborhoodName char(255), NeighborhoodURL char(255), TotalPopulation2001 char(255), TotalPopulation2011 char(255), ParkId number(6,0), RefParkId number(6,0), ParkName char(40), EWStreet char(30), NSStreet char(30), DogPark char(1), Washrooms char(1), SpecialFeatures char(1), _clipped char(3)

Bookmark: Parks Reader
Parks (reader POSTGIS_1)
    attributes: ParkId int2, RefParkId int2, ParkName char(40), NeighborhoodName char(40), EWStreet char(30), NSStreet char(30), DogPark char(1), Washrooms char(1), SpecialFeatures char(1)
    -> Clipper [CANDIDATE]

Bookmark: Neighborhoods Reader
Neighborhoods (reader POSTGIS_1)
    attributes: NeighborhoodId text, NeighborhoodName text, NeighborhoodURL text, TotalPopulation2001 text, TotalPopulation2011 text
    -> Clipper [CLIPPER]
