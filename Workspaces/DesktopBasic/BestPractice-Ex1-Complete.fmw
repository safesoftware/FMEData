FME workspace BestPractice-Ex1-Complete.fmw
Title: BestPractice-Ex1-Complete

Parameters:
- SourceDataset_MITAB = C:\FMEData2019\Data\Parks\Parks.tab   # Source MapInfo TAB File(s)
- SourceDataset_CSV2 = C:\FMEData2019\Data\Emergency\Crime.csv   # Source CSV (Comma Separated Value) File(s)
- SourceDataset_OSM = C:\FMEData2019\Data\OpenStreetMap\leisure.osm   # Source OpenStreetMap File(s)

Readers:
- FILEGDB_1: FILEGDB from C:\FMEData2019\Data\Addresses\Addresses.gdb
- MITAB_1: MITAB from $(SourceDataset_MITAB)
- CSV2_1: CSV2 from $(SourceDataset_CSV2)
- OSM_1: OSM from $(SourceDataset_OSM)

PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> AttributeSplitter
AttributeSplitter
    ATTR_NAME = PSTLADDRESS
    DELIMITER = " "
    DROP_EMPTY_PARTS = No
    LIST_NAME = _list
    TRIM_OPTION = Both
    -> AttributeManager
AttributeManager
    ATTR_TABLE:
      REMOVE OBJECTID
      REMOVE GlobalID
      REMOVE OWNERNM1
      REMOVE OWNERNM2
      RENAME_SET_VALUE PSTLCITY > City
      RENAME_SET_VALUE PSTLPROV > Province
      REMOVE INTSTATE
      REMOVE INTPSTLCD
      RENAME_SET_VALUE COUNTRY > Country
      REMOVE REPRESENT
      REMOVE STATUS
      REMOVE LASTUPDATE
      REMOVE LASTEDITOR
      RENAME_SET_VALUE POSTALCODE > PostalCode
      SET_TO Number = @Value(_list{0})
      SET_TO Street = @Value(_list{1}) @Value(_list{2}) @Value(_list{3})
    -> StringReplacer
StringReplacer
    CASE = NO
    FIND_TEXT = ..$
    NO_MATCH = _FME_NO_OP_
    REGEXP = YES
    REPLACE_TEXT = XX
    SRC_ATTRS = Number
    -> StringCaseChanger
StringCaseChanger
    ATTRCHOICE = Selected Attributes
    ATTRLIST = Street
    CHANGE_TYPE = UPPERCASE
    -> AttributeManager_2
AttributeManager_2
    ATTR_TABLE = SET_TO JoinKey = @Trim(@Value(Number) @Value(Street))
    -> FeatureJoiner [LEFT]
PostcodeBoundaries (reader FILEGDB_1)
    attributes: OBJECTID objectid, CFSAUID text(3), SHAPE_Length double, SHAPE_Area double
Crime (reader CSV2_1)
    attributes: ID string, Type string, Month string, Block string
    -> FeatureJoiner [RIGHT]
FeatureJoiner
    ATTR_CONFLICT_RES = Use Left
    GEOMETRY_HANDLING = Use Left
    JOIN_KEYS = JoinKey Block AUTO
    JOIN_MODE = Inner
    JOINED -> AttributeValueMapper
    UNJOINED_LEFT -> AttributeCreator
AttributeValueMapper
    DIRECTION = Forward (Source To Destination)
    LUT = Commercial BE,10,Mischief Over $5000,8,Mischief Under $5000,2,Thef Of Auto Under $5000,4,Theft From Auto Over $5000,7,Theft From Auto Under $5000,3,Theft Of Auto Over $5000,6
    SRC = Type
    VAL_ATTR = CrimeValue
    -> Aggregator
Aggregator
    ACCUM_ATTRS_NAME = Drop Incoming Attributes
    AGGREGATE_TYPE = Homogeneous Collection (If Possible)
    GROUP_BY = PSTLADDRESS
    LIST_ATTRS_TO_INCLUDE = _list{} Block City Country CrimeValue ID JoinKey Month Number PostalCode Province PSTLADDRESS Street Type
    LIST_NAME = CrimeList
    MODE = Geometry - Assemble One Level
    SEP = ,
    SUM = CrimeValue
    AGGREGATE -> CenterPointReplacer
CenterPointReplacer
    POINTTYPE = CENTER
    POINT -> NeighborFinder [BASE]
AttributeCreator
    ATTR_TABLE = SET_TO CrimeValue = 0
    -> NeighborFinder [BASE]
Creator
    GEOMTYPE = Geometry Object
    NUM = 1
    CREATED -> FeatureReader [INITIATOR]
FeatureReader
    ATTRIBUTES = BusinessImprovementAreas,"AreaID,AreaName,LastUpdated",HistoricAreas,"ZoneID,ZoneName,ZoneCategory,ZoneLocation,ZoneDescription,ZonePoliciesPDF,LastUpdated",NoiseControlAreas,"AreaID,AreaName,AreaDescription,LastUpdated",ViewCones,"ViewID,ViewDescription,LastUpdated"
    ATTR_ACCUM_MODE = Only Use Result
    COMBINE_GEOM = Use Result
    DATASET = C:\FMEData2019\Data\Planning\PlanningRestrictions.gpkg
    FEATURETYPES = NoiseControlAreas
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    GEOPACKAGE_USE_SEARCH_ENVELOPE = NO
    INTERACT = <No Spatial Filter>
    OUTPUT_FEATURES_DISPLAY = Schema and Data Features
    NoiseControlAreas -> PointOnAreaOverlayer [AREA]
leisure (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, sport xml_buffer, source xml_buffer, type xml_buffer, access xml_buffer, addr:street xml_buffer, website xml_buffer, boundary xml_buffer, building xml_buffer, name xml_buffer, leisure xml_buffer
    -> Tester
Tester
    BOOL_OP = OR
    COMPOSITE_TEST = 1
    TEST_CLAUSE = TEST @Value(leisure) = swimming_pool
    TEST_MODE = TEST
    PASSED -> Reprojector
Reprojector
    DEST = UTM83-10
    INTERPOLATION_TYPE_NAME = Nearest Neighbor
    RASTER_CELL_SIZE = Preserve Cells
    RASTER_TOLERANCE = 0.0
    SOURCE = Read from feature
    REPROJECTED -> NeighborFinder [CANDIDATE]
Parks (reader MITAB_1) [off]
    attributes: ParkId smallint, RefParkId smallint, ParkName char(40), NeighborhoodName char(40), VisitorCount smallint, TreeCount smallint, DogPark char(1), Washrooms char(1), SpecialFeatures char(1)
    -> NeighborFinder [CANDIDATE]
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> AttributeRenamer
AttributeRenamer
    ATTR_TABLE = RENAME_SET_DEFAULT _distance > PoolDistance
    -> PointOnAreaOverlayer [POINT]
PointOnAreaOverlayer
    ATTR_ACCUM_MODE = Merge Incoming
    ATTR_CONFLICT_RES = Use Original
    DEAGGREGATE_INPUT = Yes
    OV_ATTR = _overlaps
    POLYS_FIRST = NO
    POINT -> AttributeValueMapper_2
AttributeValueMapper_2
    DEFAULT_VALUE = 0
    DIRECTION = Forward (Source To Destination)
    LUT = Schedule C,200,Schedule F,50,Intermediate,100
    SRC = AreaName
    VAL_ATTR = NoiseZoneScore
    -> ExpressionEvaluator
ExpressionEvaluator
    ACTION = Create New Attribute
    EXPRESSION = @Value(PoolDistance) + @Value(CrimeValue) - @Value(NoiseZoneScore)
    VAL_ATTR = Walkability
