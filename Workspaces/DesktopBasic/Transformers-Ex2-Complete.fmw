FME workspace Transformers-Ex2-Complete.fmw

Parameters:
- DestDataset_XLSXW = C:\FMEData2019\Output\Training\AddressFile.xlsx   # Destination Microsoft Excel File

Writers:
- XLSXW_1: XLSXW to $(DestDataset_XLSXW)

Creator
    GEOMTYPE = Geometry Object
    NUM = 1
    CREATED -> FeatureReader [INITIATOR]
FeatureReader
    ATTRIBUTES = PostalAddress,"OBJECTID,GlobalID,OWNERNM1,OWNERNM2,PSTLADDRESS,PSTLCITY,PSTLPROV,INTSTATE,INTPSTLCD,COUNTRY,REPRESENT,STATUS,LASTUPDATE,LASTEDITOR,POSTALCODE",PostcodeBoundaries,"OBJECTID,CFSAUID,SHAPE_Length,SHAPE_Area"
    ATTR_ACCUM_MODE = Only Use Result
    COMBINE_GEOM = Use Result
    DATASET = C:\FMEData2019\Data\Addresses\Addresses.gdb
    FEATURETYPES = PostalAddress
    FILEGDB_QUERY_FEATURE_TYPES_FOR_MERGE_FILTERS = Yes
    FILEGDB_SIMPLE_DONUT_GEOMETRY = simple
    FILEGDB_STRIP_GUID_GLOBALID_BRACES = yes
    FILEGDB_USE_SEARCH_ENVELOPE = NO
    FORMAT = FILEGDB
    INTERACT = <No Spatial Filter>
    OUTPUT_FEATURES_DISPLAY = Schema and Data Features
    PostalAddress -> AttributeSplitter
AttributeSplitter
    ATTR_NAME = PSTLADDRESS
    DELIMITER = " "
    DROP_EMPTY_PARTS = No
    LIST_NAME = _list
    TRIM_OPTION = Both
    -> AttributeManager
AttributeManager
    ATTR_TABLE:
      REMOVE OBJECTID
      REMOVE GlobalID
      REMOVE OWNERNM1
      REMOVE OWNERNM2
      RENAME_SET_VALUE PSTLCITY > City
      RENAME_SET_VALUE PSTLPROV > Province
      REMOVE INTSTATE
      REMOVE INTPSTLCD
      RENAME_SET_VALUE COUNTRY > Country
      REMOVE REPRESENT
      REMOVE STATUS
      REMOVE LASTUPDATE
      REMOVE LASTEDITOR
      RENAME_SET_VALUE POSTALCODE > PostalCode
      SET_TO Provider = Safe Software
      SET_TO UpdateDate = @DateTimeNow()
      SET_TO Number = @Value(_list{0})
      SET_TO Street = @Value(_list{1}) @Value(_list{2}) @Value(_list{3})
    -> PostalAddress (writer XLSXW_1)
PostalAddress (writer XLSXW_1)
    attributes: Number string(7), Street string(7), City string(5), Province string(9), PostalCode string(11), Country string(8), Provider string(9), UpdateDate string(11), Event string(6)
