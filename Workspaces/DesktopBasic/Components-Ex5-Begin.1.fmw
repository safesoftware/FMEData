FME workspace Components-Ex5-Begin.1.fmw

Parameters:
- SourceDataset_MITAB = C:\FMEData2017\Data\Parks\Parks.tab   # Source MapInfo TAB File(s)
- DestDataset_OGCKML = C:\FMEData2017\Output\Training\FundraisingWalk.kml   # Destination Google KML File
- SourceDataset_CSV2 = C:\FMEData2017\Data\GPS\WalkingTrail.csv   # Source CSV (Comma Separated Value) File(s)
- SourceDataset_FILEGDB = C:\FMEData2017\Data\CommunityMapping\CommunityMap.gdb   # File Geodatabase
- SourceDataset_GML = ""C:\FMEData2017\Data\OpenStreetMap\amenity.gml" "C:\FMEData2017\Data\OpenStreetMap\highway.gml""   # Source Geography Markup Language (GML) File(s)

Readers:
- MITAB_1: MITAB from $(SourceDataset_MITAB)
- CSV2_1: CSV2 from $(SourceDataset_CSV2) in LL84
- FILEGDB_1: FILEGDB from $(SourceDataset_FILEGDB)
- GML_1: GML from $(SourceDataset_GML)

Writers:
- OGCKML_1: OGCKML to $(DestDataset_OGCKML)

Parks (reader MITAB_1)
    attributes: ParkId smallint, RefParkId smallint, ParkName char(40), NeighborhoodName char(40), EWStreet char(30), NSStreet char(30), DogPark char(1), Washrooms char(1), SpecialFeatures char(1)
    -> Tester
Tester
    TEST_CLAUSE = TEST @Value(ParkName) = Stanley Park
    TEST_MODE = Automatic
    TEST_DESCRIPTION = ""
    BOOL_OP = OR
    PASSED -> Reprojector
    PASSED -> Clipper [CLIPPER]
CSV (reader CSV2_1)
    attributes: PointID string, Latitude y_coordinate, Longitude x_coordinate, Elevation string, Time string
    -> Reprojector
DrinkingFountains (reader FILEGDB_1)
    attributes: FountainID smallint, Location text(48), Maintainer text(16), OBJECTID objectid
    -> Reprojector
amenity_parking (reader GML_1)
    attributes: amenity xml_char(8), nd{}.ref xml_buffer, uid xml_buffer, changeset xml_buffer, tag{}.v xml_buffer, tag{}.k xml_buffer, user xml_buffer, id xml_buffer, version xml_buffer, timestamp xml_buffer, visible xml_buffer, gml_pointProperty xml_geometry, gml_multiPointProperty xml_geometry, gml_surfaceProperty xml_geometry, gml_multiSurfaceProperty xml_geometry
    -> Reprojector
Reprojector
    RASTER_CELL_SIZE = Preserve Cells
    SOURCE = Read from feature
    INTERPOLATION_TYPE_NAME = Nearest Neighbor
    DEST = UTM83-10
    REPROJECTED -> Clipper [CLIPPEE]
Clipper
    CLIPPED_ATTR = _clipped
    ATTR_ACCUM_MODE = Merge Clipper
    VAL_SOURCE = Clippee Only
    CLIP_TYPE = Multiple Clippers
    BOUNDARY_CASES = Treat as Inside
    PRESERVE_CLIPPEE_EXTENTS = No
    MEASURE_TYPE = Continuous
    MISSING_VAL_MODE = Compute
    LINES_AS_SEGMENTS = No
    CONNECT_Z_MODE = First Wins
    DEFAULT_VAL = 0
    ATTR_CONFLICT_RES = Use Clippee
    CREATE_AGGREGATES = Yes
    INSIDE -> Clipper_Inside
    OUTSIDE -> Clipper_Outside
    <REJECTED> -> Clipper__Rejected_
Clipper_Inside: Inspector
Clipper_Outside: Inspector
Clipper__Rejected_: Inspector
Parks (writer OGCKML_1)
    attributes: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
