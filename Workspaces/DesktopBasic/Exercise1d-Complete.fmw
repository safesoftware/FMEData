FME workspace Exercise1d-Complete.fmw

Parameters:
- SourceDataset_FILEGDB = C:\FMEData2015\Data\CommunityMapping\CommunityMap.gdb   # Source Geodatabase
- DestDataset_GPXX = C:\FMEData2015\Output\Training\FoodVendors.gpx   # Destination GPS eXchange Format (GPX) File

Readers:
- FILEGDB_1: FILEGDB from $(SourceDataset_FILEGDB)

Writers:
- GPXX_1: GPXX to $(DestDataset_GPXX)

FoodVendors (reader FILEGDB_1)
    attributes: VendorID smallint, VendorName text(48), VendorDescription text(16), OBJECTID objectid
    -> WayPoint (writer GPXX_1)
WayPoint (writer GPXX_1)
    attributes: elevation xml_real64, creation_time xml_buffer, magnetic_variation xml_real64, geoid_height xml_real64, name xml_buffer, comment xml_buffer, description xml_buffer, source xml_buffer, link{}.url xml_buffer, link{}.text xml_buffer, link{}.type xml_buffer, symbol xml_buffer, type xml_buffer, gps_fix_type xml_buffer, number_of_satellites xml_uint16, hdop xml_real64, vdop xml_real64, pdop xml_real64, age_of_dgps_data xml_real64, dgps_id xml_buffer, garmin_proximity xml_real64, garmin_temperature xml_real64, garmin_depth xml_real64, garmin_display_mode xml_buffer, garmin_address_street_address_1 xml_buffer, garmin_address_street_address_2 xml_buffer, garmin_address_city xml_buffer, garmin_address_state xml_buffer, garmin_address_country xml_buffer, garmin_address_postal_code xml_buffer,
      garmin_categories{} xml_buffer, extensions{} xml_xml
TrackPoint (writer GPXX_1)
    attributes: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
Track (writer GPXX_1)
    attributes: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
RoutePoint (writer GPXX_1)
    attributes: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
Route (writer GPXX_1)
    attributes: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
Metadata (writer GPXX_1)
    attributes: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
