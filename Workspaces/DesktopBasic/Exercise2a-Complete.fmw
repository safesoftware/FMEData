FME workspace Exercise2a-Complete.fmw

Parameters:
- SourceDataset_MITAB = C:\FMEData2015\Data\Parks\Parks.tab   # Source MapInfo TAB (MITAB) File(s)
- DestDataset_MITAB = C:\FMEData2015\Output\Training   # Destination MapInfo Folder

Readers:
- MITAB_1: MITAB from $(SourceDataset_MITAB)

Writers:
- MITAB_2: MITAB to $(DestDataset_MITAB)

Parks (reader MITAB_1)
    attributes: ParkId smallint, RefParkId smallint, ParkName char(40), NeighborhoodName char(40), EWStreet char(30), NSStreet char(30), DogPark char(1), Washrooms char(1), SpecialFeatures char(1)
    -> ParksMaintenanceData (writer MITAB_2)
ParksMaintenanceData (writer MITAB_2)
    attributes: ParkId smallint, ParkName char(40), Neighborhood char(40), ParkArea float, AverageParkArea float
