FME workspace Exercise5c-Complete-Advanced.fmw

Parameters:
- SourceDataset_CSV = C:\FMEData2015\Data\Emergency\Crime2011.csv   # Source CSV (CommaSeparatedValue) File(s)
- SourceDataset_ACAD = C:\FMEData2015\Data\Transportation\Roads.dwg   # Source Autodesk AutoCAD DWG/DXF File(s)
- FEATURE_TYPES =

Readers:
- CSV_1: CSV from $(SourceDataset_CSV)
- ACAD_1: ACAD from $(SourceDataset_ACAD)

Other (reader ACAD_1)
    attributes: StreetId number(6,0), StreetName char(20), From_HBlock number(5,0), HBlock char(13)
    -> StringCaseChanger
StringCaseChanger
    CHANGE_TYPE = UPPERCASE
    ATTRLIST = HBlock
    ATTRCHOICE = Selected Attributes
    -> FeatureMerger [input 1]
CSV (reader CSV_1)
    attributes: CrimeID number(4,0), Type char(28), Month number(2,0), Block char(19)
    -> StringReplacer
StringReplacer
    REGEXP = no
    CASE = no
    SRC_ATTRS = Block
    NO_MATCH = _FME_NO_OP_
    REPLACE_TEXT = 00
    FIND_TEXT = XX
    -> FeatureMerger [input 2]
FeatureMerger
    MERGE_TYPE = Attributes Only
    MERGE_COUNT_ATTR = NumberOfCrimes
    JOIN_KEYS = @Value(HBlock) @Value(Block) STRING
    GEOM_TYPE = Build Polygons
    LIST_NAME = CrimeList
    SUPPLIERS_FIRST = No
    ATTR_ACCUM_MODE = Merge Supplier
    ATTR_CONFLICT_RES = Use Requestor
    PROCESS_DUPS = Yes
    MERGED -> MapnikRasterizer
MapnikRasterizer
    NUM_ROWS = 2500
    COLROW_OR_SPACING = Columns and Rows
    MAPNIK_CONFIG = Output;line;__ignore__color-group;;stroke;0,0,0;stroke-opacity;1;__ignore__line-style-group;;stroke-width;@Value(NumberOfCrimes);stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over
    LAYER_CARDINALITY = Each rendering rule is a layer
    BACKGROUND_COLOR = 1,1,1
    NUM_COLUMNS = 2500
    INTERPRETATION_TYPE = RGBA32
    BACKGROUND_COLOR_ALPHA = 1.0
    SPECIFY_GROUND_EXTENTS = Use input data ground extents
    RASTER -> MapnikRasterizer_Raster
MapnikRasterizer_Raster: Inspector
