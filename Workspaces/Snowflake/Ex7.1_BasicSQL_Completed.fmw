FME workspace Ex7.1_BasicSQL_Completed.fmw

Parameters:
- SourceDataset_SNOWFLAKE_NONSPATIAL = Snowflake Sample   # Connection

Readers:
- SNOWFLAKE_NONSPATIAL_1: SNOWFLAKE_NONSPATIAL from $(SourceDataset_SNOWFLAKE_NONSPATIAL)

Bookmark: Let the Database do the work - Example 1
Note: Using sample data in TPCH_SF1 schema
Note: Record Counts / select count(*) as cust_count from "SNOWFLAKE_SAMPLE_DATA"."TPCH_SF1"."CUSTOMER"; -- 150,000 / select count(*) as cust_count from "SNOWFLAKE_SAMPLE_DATA"."TPCH_SF1"."ORDERS"; --1,500,000 / select count(*) as cust_count from "SNOWFLAKE_SAMPLE_DATA"."TPCH_SF1"."LINEITEM"; --6,000,000 / select count(*) as cust_count from "SNOWFLAKE_SAMPLE_DATA"."TPCH_SF1"."PART"; -- 200,000
Note: select c.C_NAME, c.C_ACCTBAL, C_MKTSEGMENT, o.O_ORDERKEY, / o.O_ORDERSTATUS, o.O_TOTALPRICE, l.L_ORDERKEY, / l.L_PARTKEY, p.P_NAME, p.P_RETAILPRICE / from / CUSTOMER c, ORDERS o, LINEITEM l, PART p / where / c.C_CUSTKEY=o.O_CUSTKEY / and o.O_ORDERKEY = l.L_ORDERKEY / and l.L_PARTKEY=p.P_PARTKEY / and (l.L_ORDERKEY between 5400001 and 5400100) / and c.C_MKTSEGMENT= 'HOUSEHOLD' / and c.C_NAME like '%00005%';
SQLCreator [off]
    DATASET = Snowflake Sample
    EXPOSED_ATTRIBUTE_LIST = C_ACCTBAL,C_MKTSEGMENT,C_NAME,L_ORDERKEY,L_PARTKEY,O_ORDERKEY,O_ORDERSTATUS,O_TOTALPRICE,P_NAME,P_RETAILPRICE
    FORMAT = SNOWFLAKE_NONSPATIAL
    SNOWFLAKE_NONSPATIAL_CREATE_FEATURE_TABLES_FROM_DATA = Yes
    SNOWFLAKE_NONSPATIAL_NAMED_CONNECTION = Snowflake Sample
    SNOWFLAKE_NONSPATIAL_QUERY_FEATURE_TYPES_FOR_MERGE_FILTERS = Yes
    SNOWFLAKE_NONSPATIAL_QUERY_TIMEOUT = 30
    SQL_STATEMENT:
      select c.C_NAME, c.C_ACCTBAL, C_MKTSEGMENT, o.O_ORDERKEY,
          o.O_ORDERSTATUS, o.O_TOTALPRICE, l.L_ORDERKEY,
          l.L_PARTKEY, p.P_NAME, p.P_RETAILPRICE
       from CUSTOMER c, ORDERS o, LINEITEM l, PART p
      where c.C_CUSTKEY=o.O_CUSTKEY and o.O_ORDERKEY = l.L_ORDERKEY and l.L_PARTKEY=p.P_PARTKEY
        and (l.L_ORDERKEY between 5400001 and 5400100) and c.C_MKTSEGMENT= 'HOUSEHOLD'
        and c.C_NAME like '%00005%';
    RESULT -> SQLCreator_Result
    <REJECTED> -> SQLCreator__Rejected_
SQLCreator_Result: Inspector
SQLCreator__Rejected_: Inspector

Bookmark: Let the Database do the work - Example 2
Note: Sum All Orders (TOTAL) for customers during 1993
Note: select distinct c.C_NAME, / sum (o.O_TOTALPRICE) as TOTAL / from / ORDERS o, CUSTOMER c / where / c.C_CUSTKEY=o.O_CUSTKEY / and o.O_ORDERDATE > '1994-01-01' / and o.O_ORDERDATE < '1994-12-31' / group by c.C_NAME / order by TOTAL DESC;
SQLCreator_2 [off]
    DATASET = Snowflake Sample
    EXPOSED_ATTRIBUTE_LIST = C_NAME,TOTAL
    FORMAT = SNOWFLAKE_NONSPATIAL
    SNOWFLAKE_NONSPATIAL_CREATE_FEATURE_TABLES_FROM_DATA = Yes
    SNOWFLAKE_NONSPATIAL_NAMED_CONNECTION = Snowflake Sample
    SNOWFLAKE_NONSPATIAL_QUERY_FEATURE_TYPES_FOR_MERGE_FILTERS = Yes
    SNOWFLAKE_NONSPATIAL_QUERY_TIMEOUT = 30
    SQL_STATEMENT:
      select distinct c.C_NAME, sum (o.O_TOTALPRICE) as TOTAL
        from ORDERS o, CUSTOMER c
       where c.C_CUSTKEY=o.O_CUSTKEY
         and o.O_ORDERDATE > '1994-01-01' and o.O_ORDERDATE < '1994-12-31'
       group by c.C_NAME
       order by TOTAL DESC;
    RESULT -> Tester
Note: Greater than 2 Million in Orders
Tester
    BOOL_OP = OR
    COMPOSITE_TEST = 1
    TEST_CLAUSE = TEST @Value(TOTAL) > 2000000
    TEST_MODE = TEST
    PASSED -> SQLExecutor [INITIATOR]
Note: Now grab Region and Nation and Customer Phone Number
Note: select c.C_NAME, c.C_NATIONKEY, c.C_PHONE, c.C_MKTSEGMENT, / n.N_NAME, n.N_REGIONKEY, r.R_NAME / from / CUSTOMER c, NATION n, REGION r / where / c.C_NATIONKEY = n.N_NATIONKEY / and n.N_REGIONKEY = r.R_REGIONKEY / and C_NAME like '@Value(C_NAME)' / order by r.R_NAME;
SQLExecutor
    COMBINE_ATTRS = Keep Initiator Attributes if Conflict
    COMBINE_GEOM = Initiator Geometry Only
    DATASET = Snowflake Sample
    EXPOSED_ATTRIBUTE_LIST = C_MKTSEGMENT,C_NAME,C_NATIONKEY,C_PHONE,N_NAME,N_REGIONKEY,R_NAME
    FORMAT = SNOWFLAKE_NONSPATIAL
    SNOWFLAKE_NONSPATIAL_CREATE_FEATURE_TABLES_FROM_DATA = Yes
    SNOWFLAKE_NONSPATIAL_NAMED_CONNECTION = Snowflake Sample
    SNOWFLAKE_NONSPATIAL_QUERY_FEATURE_TYPES_FOR_MERGE_FILTERS = Yes
    SNOWFLAKE_NONSPATIAL_QUERY_TIMEOUT = 30
    SQL_STATEMENT:
      select c.C_NAME, c.C_NATIONKEY, c.C_PHONE, c.C_MKTSEGMENT, n.N_NAME, n.N_REGIONKEY, r.R_NAME
      from CUSTOMER c, NATION n, REGION r
      where c.C_NATIONKEY = n.N_NATIONKEY and n.N_REGIONKEY = r.R_REGIONKEY
      and C_NAME like '@Value(C_NAME)'
      order by r.R_NAME;
    RESULT -> Sorter
Note: Sort by Region
Sorter
    SORT_PARM = R_NAME ALPHA ASCENDING
    SORTED -> OrdersOver2Million
Note: Write out to Excel or HTML
OrdersOver2Million: Inspector

Bookmark: How long does this take? 6 minutes and I only returned 10,000 rows from each table
CUSTOMER (reader SNOWFLAKE_NONSPATIAL_1)
    attributes: C_CUSTKEY number(38,0), C_NAME varchar(25), C_ADDRESS varchar(40), C_NATIONKEY number(38,0), C_PHONE varchar(15), C_ACCTBAL number(12,2), C_MKTSEGMENT varchar(10), C_COMMENT varchar(117)
    -> InlineQuerier [TPCH_SF1.CUSTOMER]
ORDERS (reader SNOWFLAKE_NONSPATIAL_1)
    attributes: O_ORDERKEY number(38,0), O_CUSTKEY number(38,0), O_ORDERSTATUS varchar(1), O_TOTALPRICE number(12,2), O_ORDERDATE date, O_ORDERPRIORITY varchar(15), O_CLERK varchar(15), O_SHIPPRIORITY number(38,0), O_COMMENT varchar(79)
    -> InlineQuerier [TPCH_SF1.ORDERS]
LINEITEM (reader SNOWFLAKE_NONSPATIAL_1)
    attributes: L_ORDERKEY number(38,0), L_PARTKEY number(38,0), L_SUPPKEY number(38,0), L_LINENUMBER number(38,0), L_QUANTITY number(12,2), L_EXTENDEDPRICE number(12,2), L_DISCOUNT number(12,2), L_TAX number(12,2), L_RETURNFLAG varchar(1), L_LINESTATUS varchar(1), L_SHIPDATE date, L_COMMITDATE date, L_RECEIPTDATE date, L_SHIPINSTRUCT varchar(25), L_SHIPMODE varchar(10), L_COMMENT varchar(44)
    -> InlineQuerier [TPCH_SF1.LINEITEM]
PART (reader SNOWFLAKE_NONSPATIAL_1)
    attributes: P_PARTKEY number(38,0), P_NAME varchar(55), P_MFGR varchar(25), P_BRAND varchar(10), P_TYPE varchar(25), P_SIZE number(38,0), P_CONTAINER varchar(10), P_RETAILPRICE number(12,2), P_COMMENT varchar(23)
    -> InlineQuerier [TPCH_SF1.PART]
Note: Great for doing SQL like queries in FME
InlineQuerier
    QUERY_DEF:
      Result,
      select c.C_NAME, c.C_ACCTBAL, C_MKTSEGMENT, o.O_ORDERKEY,
      o.O_ORDERSTATUS, o.O_TOTALPRICE, l.L_ORDERKEY,
      l.L_PARTKEY, p.P_NAME, p.P_RETAILPRICE
      from "TPCH_SF1.CUSTOMER" c,"TPCH_SF1.LINEITEM" l,"TPCH_SF1.ORDERS" o,"TPCH_SF1.PART" p
      where c.C_CUSTKEY=o.O_CUSTKEY and o.O_ORDERKEY = l.L_ORDERKEY and l.L_PARTKEY=p.P_PARTKEY
      and (l.L_ORDERKEY between 5400001 and 5400100) and c.C_MKTSEGMENT= 'HOUSEHOLD'
      and c.C_NAME like '%00005%';,FIRST
    QUERY_SCHEMA = Result,C_NAME,varchar(25),C_ACCTBAL,"real(12,2)",C_MKTSEGMENT,varchar(10),O_ORDERKEY,"real(38,0)",O_ORDERSTATUS,varchar(1),O_TOTALPRICE,"real(12,2)",L_ORDERKEY,"real(38,0)",L_PARTKEY,"real(38,0)",P_NAME,varchar(55),P_RETAILPRICE,"real(12,2)"
    TABLE_DEF = TPCH_SF1.CUSTOMER,C_CUSTKEY,"real(38,0)",C_NAME,varchar(25),C_ADDRESS,varchar(40),C_NATIONKEY,"real(38,0)",C_PHONE,varchar(15),C_ACCTBAL,"real(12,2)",C_MKTSEGMENT,varchar(10),C_COMMENT,varchar(117),TPCH_SF1.ORDERS,O_ORDERKEY,"real(38,0)",O_CUSTKEY,"real(38,0)",O_ORDERSTATUS,varchar(1),O_TOTALPRICE,"real(12,2)",O_ORDERDATE,text,O_ORDERPRIORITY,varchar(15),O_CLERK,varchar(15),O_SHIPPRIORITY,"real(38,0)",O_COMMENT,varchar(79),TPCH_SF1.LINEITEM,L_ORDERKEY,"real(38,0)",L_PARTKEY,"real(38,0)",L_SUPPKEY,"real(38,0)",L_LINENUMBER,"real(38,0)",L_QUANTITY,"real(12,2)",L_EXTENDEDPRICE,"real(12,2)",L_DISCOUNT,"real(12,2)",L_TAX,"real(12,2)",L_RETURNFLAG,varchar(1),L_LINESTATUS,varchar(1),L_SHIPDATE,text,L_COMMITDATE,text,L_RECEIPTDATE,text,L_SHIPINSTRUCT,varchar(25),L_SHIPMODE,varchar(10),L_COMMENT,varchar(44),TPCH_SF1.PART,P_PARTKEY,"real(38,0)",P_NAME,varchar(55),P_MFGR,varchar(25),P_BRAND,varchar(10),P_TYPE,varchar(25),P_SIZE,"real(38,0)",P_CONTAINER,varchar(10),P_RETAILPRICE,"real(12,2)",P_COMMENT,varchar(23)
    Result -> InlineQuerier_Result
InlineQuerier_Result: Inspector
NATION (reader SNOWFLAKE_NONSPATIAL_1) [off]
    attributes: N_NATIONKEY number(38,0), N_NAME varchar(25), N_REGIONKEY number(38,0), N_COMMENT varchar(152)

Bookmark: Instructions
Note: Instructions / Bookmark - Example 1 / 1) In the Naviagtor Pane expand the Database Connections and update the connection if necessary. Set it to "Snowflake Sample". Your connection name could be different. / 2) Review the SQL in the SQLCreator of Example 1 bookmark. / 3) Enable the SQLCreator and run the workspace. / 4) Disable the SQLCreator. / 5) Reivew the Translation Log / NOTE: Notice the time the workspaces completes in. The query is working with nearly 8,000,000 rows of data. / Bookmark - Example 2 / 1) Review the SQL in the SQLCreator of Example 2 bookmark. / 2) Enable the SQLCreator and run the workspace. / 3) Review the Translation Log / NOTE: Notice the time the workspace too to run.This example just shows chaining together an SQLCreator and SQLExecuter. Again, this workflow could have been all in FME but it would have taken consider more time to complete and used more resources. / Example 3 / This is an example of the Snowflake Reader being used and then an InlineQuerier, performing a similar query to Example 2. / You do not need to run this... it will take minutes instead of seconds to complete. / Let the database do the work. / Worth noticing also... on the Reader, I've read all the 1000 features... but FME still has pulled all the data back from the database. Remember, this Max Features to Read Per Feature Type is after it gets to FME. So that 6 million record LINEITEM table is being in its entirety.
