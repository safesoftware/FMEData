FME workspace Ex2.0_Reading_Completed.fmw

Parameters:
- SourceDataset_SNOWFLAKE_NONSPATIAL = Snowflake Sample   # Connection

Readers:
- SNOWFLAKE_NONSPATIAL_1: SNOWFLAKE_NONSPATIAL from $(SourceDataset_SNOWFLAKE_NONSPATIAL)

CUSTOMER (reader SNOWFLAKE_NONSPATIAL_1)
    attributes: C_CUSTKEY number(38,0), C_NAME varchar(25), C_ADDRESS varchar(40), C_NATIONKEY number(38,0), C_PHONE varchar(15), C_ACCTBAL number(12,2), C_MKTSEGMENT varchar(10), C_COMMENT varchar(117)
    -> TPCH_SF1.CUSTOMER
TPCH_SF1.CUSTOMER: Inspector
