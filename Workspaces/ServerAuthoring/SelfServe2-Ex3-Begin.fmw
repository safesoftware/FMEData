FME workspace SelfServe2-Ex3-Begin.fmw

Parameters:
- SourceDataset_GEOTIFF = C:\FMEDATA2018\Data\Orthophotos\06-07-LM.tif   # Source GeoTIFF File(s)
- FEATURE_TYPES =
- DestDataset_JPEG = C:\FMEDATA2018\Output   # Destination JPEG Folder
- CellSpacing = 50   # Enter Resolution (1-50)
- Compression =   # Yes

Readers:
- GEOTIFF_1: GEOTIFF from $(SourceDataset_GEOTIFF)

Writers:
- JPEG_1: JPEG to $(DestDataset_JPEG)

06_07_LM (reader GEOTIFF_1)
    -> RasterResampler
RasterResampler
    INTERPOLATION_TYPE_NAME = Nearest Neighbor
    ROWCOL_OR_CELLSIZE = CellSize
    X_CELL_SIZE = $(CellSpacing)
    Y_CELL_SIZE = $(CellSpacing)
    RESAMPLED -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> 06_07_LM (writer JPEG_1)
06_07_LM (writer JPEG_1)
