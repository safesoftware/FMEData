FME workspace SelfServe-Ex6-Complete.fmw

Parameters:
- FEATURE_TYPES =   # Raster Tiles to Read
- FEATURE_TYPES_2 =
- OutputCoordSys =
- OutputFormat =
- CellSpacing = 50   # Enter Resolution (1-50)
- Compression =   # Select Compression Level
- Neighborhood =   # Pleasant"%Strathcona%"West End" Select the Neighborhood

Readers:
- GEOTIFF_1: GEOTIFF from ""C:\FMEData2019\Data\Orthophotos\02-03-HI.tif" "C:\FMEData2019\Data\Orthophotos\02-03-JK.tif" "C:\FMEData2019\Data\Orthophotos\02-03-LM.tif" "C:\FMEData2019\Data\Orthophotos\02-03-NO.tif" "C:\FMEData2019\Data\Orthophotos\04-05-HI.tif" "C:\FMEData2019\Data\Orthophotos\04-05-JK.tif" "C:\FMEData2019\Data\Orthophotos\04-05-LM.tif" "C:\FMEData2019\Data\Orthophotos\04-05-NO.tif" "C:\FMEData2019\Data\Orthophotos\04-05-PQ.tif" "C:\FMEData2019\Data\Orthophotos\04-05-RS.tif" "C:\FMEData2019\Data\Orthophotos\06-07-HI.tif" "C:\FMEData2019\Data\Orthophotos\06-07-JK.tif" "C:\FMEData2019\Data\Orthophotos\06-07-LM.tif" "C:\FMEData2019\Data\Orthophotos\06-07-NO.tif" "C:\FMEData2019\Data\Orthophotos\06-07-PQ.tif" "C:\FMEData2019\Data\Orthophotos\06-07-RS.tif" "C:\FMEData2019\Data\Orthophotos\08-09-HI.tif" "C:\FMEData2019\Data\Orthophotos\08-09-JK.tif" "C:\FMEData2019\Data\Orthophotos\08-09-LM.tif" "C:\FMEData2019\Data\Orthophotos\08-09-NO.tif" "C:\FMEData2019\Data\Orthophotos\08-09-PQ.tif" "C:\FMEData2019\Data\Orthophotos\08-09-RS.tif" "C:\FMEData2019\Data\Orthophotos\10-11-HI.tif" "C:\FMEData2019\Data\Orthophotos\10-11-JK.tif" "C:\FMEData2019\Data\Orthophotos\10-11-LM.tif" "C:\FMEData2019\Data\Orthophotos\10-11-NO.tif" "C:\FMEData2019\Data\Orthophotos\10-11-PQ.tif" "C:\FMEData2019\Data\Orthophotos\10-11-RS.tif" "C:\FMEData2019\Data\Orthophotos\12-13-HI.tif" "C:\FMEData2019\Data\Orthophotos\12-13-JK.tif" "C:\FMEData2019\Data\Orthophotos\12-13-LM.tif" "C:\FMEData2019\Data\Orthophotos\12-13-NO.tif" "C:\FMEData2019\Data\Orthophotos\12-13-PQ.tif" "C:\FMEData2019\Data\Orthophotos\12-13-RS.tif" "C:\FMEData2019\Data\Orthophotos\14-15-HI.tif" "C:\FMEData2019\Data\Orthophotos\14-15-JK.tif" "C:\FMEData2019\Data\Orthophotos\14-15-LM.tif" "C:\FMEData2019\Data\Orthophotos\14-15-NO.tif" "C:\FMEData2019\Data\Orthophotos\14-15-PQ.tif" "C:\FMEData2019\Data\Orthophotos\14-15-RS.tif""
- DGNV8_1: DGNV8 from C:\FMEData2019\Data\Transportation\RoadsDGN.dgn
- OGCKML_1: OGCKML from C:\FMEData2019\Data\Boundaries\VancouverNeighborhoods.kml

Writers:
- JPEG_1: JPEG to C:\FMEData2019\Output\Training
- GENERIC_1: GENERIC to C:\FMEData2019\Output in $(OutputCoordSys)

06_07_LM (reader GEOTIFF_1)
    -> RasterResampler
RasterResampler
    INTERPOLATION_TYPE_NAME = Nearest Neighbor
    ROWCOL_OR_CELLSIZE = CellSize
    X_CELL_SIZE = $(CellSpacing)
    Y_CELL_SIZE = $(CellSpacing)
    RESAMPLED -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> VectorOnRasterOverlayer [RASTER]
Neighborhoods (reader OGCKML_1)
    attributes: NeighborhoodId kml_buffer, NeighborhoodName kml_buffer, NeighborhoodURL kml_buffer, TotalPopulation2001 kml_buffer, TotalPopulation2011 kml_buffer
    -> Tester
Tester
    BOOL_OP = OR
    COMPOSITE_TEST = 1
    TEST_CLAUSE = TEST @Value(NeighborhoodName) = $(Neighborhood)
    TEST_MODE = TEST
    PASSED -> CsmapReprojector
CsmapReprojector
    DEST = UTM83-10
    INTERPOLATION_TYPE_NAME = Nearest Neighbor
    RASTER_CELL_SIZE = Preserve Cells
    RASTER_TOLERANCE = 0.0
    VERTICAL_HANDLING = Ignore heights and leave them unchanged
    REPROJECTED -> Clipper [CLIPPER]
Arterial (reader DGNV8_1)
    -> VectorOnRasterOverlayer [VECTOR]
VectorOnRasterOverlayer
    ALPHA = 1.0
    ANTI_ALIASING = No
    COMPOSITE_USING_ALPHA_BAND = No
    TOLERANCE = 0.5
    RASTER -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> 06_07_LM (writer GENERIC_1)
Note: Generic Writer feature type
06_07_LM (writer GENERIC_1)
Note: JPEG Writer feature type
06_07_LM (writer JPEG_1)
