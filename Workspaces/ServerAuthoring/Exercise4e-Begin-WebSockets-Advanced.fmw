FME workspace Exercise4e-Begin-WebSockets-Advanced.fmw

Parameters:
- server_url = ws://localhost:7078   # WebSocket Server URL
- SourceDataset_TEXTLINE = C:\FMEData2015\Resources\sample-json.json   # Source Text File(s)

Readers:
- TEXTLINE_1: TEXTLINE from $(SourceDataset_TEXTLINE)

Note: displacer_modified.fmw / Safe Software / Last modifiec: 2015-02-04 / Processes notification from FME Server, displaces point, and returns result directly to the WebSocket server. / This is an example of the hybrid mode of WebSocket communication. This workspace will need to be configured as a subscription to the 'points' topic on FME Server.

Bookmark: Read from WebSocket and process to attributes
text_line (reader TEXTLINE_1)
    attributes: text_line_data buffer
    -> JSONExtractor
JSONExtractor
    JSON_ATTR = text_line_data
    EXTRACT_QUERY_TABLE = content json["ws_publisher_content"]
    EVALUATED -> SubstringExtractor
SubstringExtractor
    END = -2
    RESULT_ATTR = _substring
    SRC_ATTR = content
    START = 1
    -> AttributeSplitter
AttributeSplitter
    TRIM_OPTION = Both
    DROP_EMPTY_PARTS = No
    LIST_NAME = latlon
    ATTR_NAME = _substring
    DELIMITER = ,
    -> VertexCreator

Bookmark: Displace point northeast, and extract coords
VertexCreator
    YVAL = @Value(latlon{0})
    XVAL = @Value(latlon{1})
    MODE_NAME = Add Point
    -> Offsetter
Offsetter
    YOFF = 0.05
    ZOFF = 0
    XOFF = 0.05
    OFFSET -> CoordinateExtractor
CoordinateExtractor
    Z_DEFAULT = -9999
    X_ATTR = lon
    IND = 0
    Z_ATTR = _z
    Y_ATTR = lat
    -> WebSocketSender

Bookmark: Send to WebSocket server and log
Note: WebSocketSender [WebSocketSender:1] / WebSocket Server URL: $(server_url) / Connection Preamble: { / ws_op: "open", / ws_stream_id: "disp_pnts" / } / Data to Transmit: { / ws_op: 'send', / ws_msg: '{"lat": "@Value(lat)", "lon": "@Value(lon)" }' / } / Verify SSL Certificates: No / Version: 1 / Last Parameter Edit: Build 15250
WebSocketSender
    DATA:
      {
          ws_op: 'send',
          ws_msg: '{"lat": "@Value(lat)", "lon": "@Value(lon)" }'
      }
    PREAMBLE:
      {
          ws_op: "open",
          ws_stream_id: "disp_pnts"
      }
    VERIFY_SSL_CERTIFICATES = No
    HOST = $(server_url)
    -> WebSocketSender_output
WebSocketSender_output: Logger
    MESSAGE = Feature is:
    MAXFEATS = 20
    MAXCOORDS = 20
