FME workspace SelfServe-Ex4-Complete.fmw

Parameters:
- SourceDataset_GEOTIFF = C:\FMEData2019\Data\Orthophotos\06-07-LM.tif   # Source GeoTIFF File(s)
- FEATURE_TYPES =
- DestDataset_JPEG = C:\FMEData2019\Output\Training   # Destination JPEG Folder
- CellSpacing = 50   # Enter Resolution (1-50)
- Compression =   # Select Compression Level
- DestDataset_GENERIC = C:\FMEData2019\Output   # Destination Generic (Any Format) Folder
- OutputFormat =
- OutputCoordSys =

Readers:
- GEOTIFF_1: GEOTIFF from $(SourceDataset_GEOTIFF)

Writers:
- JPEG_1: JPEG to $(DestDataset_JPEG)
- GENERIC_1: GENERIC to $(DestDataset_GENERIC) in $(OutputCoordSys)

06_07_LM (reader GEOTIFF_1)
    -> RasterResampler
RasterResampler
    INTERPOLATION_TYPE_NAME = Nearest Neighbor
    ROWCOL_OR_CELLSIZE = CellSize
    X_CELL_SIZE = $(CellSpacing)
    Y_CELL_SIZE = $(CellSpacing)
    RESAMPLED -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> 06_07_LM (writer GENERIC_1)
06_07_LM (writer GENERIC_1)
06_07_LM (writer JPEG_1)
