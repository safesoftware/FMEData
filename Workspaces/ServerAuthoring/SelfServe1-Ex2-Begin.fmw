FME workspace SelfServe1-Ex2-Begin.fmw

Parameters:
- SourceDataset_GEOTIFF = C:\FMEData2018\Data\Orthophotos\06-07-LM.tif   # Source GeoTIFF File(s)
- FEATURE_TYPES =
- DestDataset_JPEG = C:\FMEData2018\Output\Training   # Destination JPEG Folder

Readers:
- GEOTIFF_1: GEOTIFF from $(SourceDataset_GEOTIFF)

Writers:
- JPEG_1: JPEG to $(DestDataset_JPEG)

06_07_LM (reader GEOTIFF_1)
    -> RasterResampler
RasterResampler
    INTERPOLATION_TYPE_NAME = Nearest Neighbor
    ROWCOL_OR_CELLSIZE = CellSize
    X_CELL_SIZE = 5
    Y_CELL_SIZE = 5
    RESAMPLED -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> 06_07_LM (writer JPEG_1)
06_07_LM (writer JPEG_1)
