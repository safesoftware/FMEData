FME workspace SelfServe-Ex3-Begin.fmw
Title: NONE to XLSXW

Parameters:
- DestDataset_GENERIC = C:\FMEData2020\Output\Training   # Destination Generic (Any Format) Folder
- FORMAT = XLSXW   # GeoPackage,OGCGEOPACKAGE%Esri Shapefile,SHAPEFILE%Microsoft Excel,XLSXW Output format

Writers:
- GENERIC_1: GENERIC to $(DestDataset_GENERIC)

Creator
    GEOMTYPE = Geometry Object
    NUM = 1
    CREATED -> FeatureReader [INITIATOR]
Note: Read in address points
FeatureReader
    ATTRIBUTES = PostalAddress,"OBJECTID,GlobalID,OWNERNM1,OWNERNM2,PSTLADDRESS,PSTLCITY,PSTLPROV,INTSTATE,INTPSTLCD,COUNTRY,REPRESENT,STATUS,LASTUPDATE,LASTEDITOR,POSTALCODE",PostcodeBoundaries,"OBJECTID,CFSAUID,SHAPE_Length,SHAPE_Area"
    ATTR_ACCUM_MODE = Only Use Result
    COMBINE_GEOM = Use Result
    DATASET = C:\FMEData2020\Data\Addresses\Addresses.gdb
    FEATURETYPES = PostalAddress
    FILEGDB_QUERY_FEATURE_TYPES_FOR_MERGE_FILTERS = Yes
    FILEGDB_SIMPLE_DONUT_GEOMETRY = simple
    FILEGDB_STRIP_GUID_GLOBALID_BRACES = no
    FILEGDB_USE_SEARCH_ENVELOPE = NO
    FORMAT = FILEGDB
    INTERACT = <No Spatial Filter>
    OUTPUT_FEATURES_DISPLAY = Schema and Data Features
    PostalAddress -> NotifyList (writer GENERIC_1)
Note: Write an table of affected addresses to Excel, Shapefile, Geopackage, or GeoJSON
NotifyList (writer GENERIC_1)
    attributes: OBJECTID int32, GlobalID buffer, OWNERNM1 varchar(150), OWNERNM2 varchar(150), PSTLADDRESS varchar(250), PSTLCITY varchar(100), PSTLPROV varchar(25), INTSTATE varchar(5), INTPSTLCD varchar(10), COUNTRY varchar(100), REPRESENT varchar(14), STATUS varchar(9), LASTUPDATE datetime, LASTEDITOR varchar(50), POSTALCODE varchar(6)
