FME workspace SelfServe2-Ex4-Begin.fmw

Parameters:
- FEATURE_TYPES =   # Raster Tiles to Read
- FEATURE_TYPES_2 =
- CellSpacing = 50   # Enter Resolution (1-50)
- Compression =   # Select Compression
- OutputFormat =
- OutputCoordSys =

Readers:
- GEOTIFF_1: GEOTIFF from ""C:\FMEData2018\Data\Orthophotos\02-03-HI.tif" "C:\FMEData2018\Data\Orthophotos\02-03-JK.tif" "C:\FMEData2018\Data\Orthophotos\02-03-LM.tif" "C:\FMEData2018\Data\Orthophotos\02-03-NO.tif" "C:\FMEData2018\Data\Orthophotos\04-05-HI.tif" "C:\FMEData2018\Data\Orthophotos\04-05-JK.tif" "C:\FMEData2018\Data\Orthophotos\04-05-LM.tif" "C:\FMEData2018\Data\Orthophotos\04-05-NO.tif" "C:\FMEData2018\Data\Orthophotos\04-05-PQ.tif" "C:\FMEData2018\Data\Orthophotos\04-05-RS.tif" "C:\FMEData2018\Data\Orthophotos\06-07-HI.tif" "C:\FMEData2018\Data\Orthophotos\06-07-JK.tif" "C:\FMEData2018\Data\Orthophotos\06-07-LM.tif" "C:\FMEData2018\Data\Orthophotos\06-07-NO.tif" "C:\FMEData2018\Data\Orthophotos\06-07-PQ.tif" "C:\FMEData2018\Data\Orthophotos\06-07-RS.tif" "C:\FMEData2018\Data\Orthophotos\08-09-HI.tif" "C:\FMEData2018\Data\Orthophotos\08-09-JK.tif" "C:\FMEData2018\Data\Orthophotos\08-09-LM.tif" "C:\FMEData2018\Data\Orthophotos\08-09-NO.tif" "C:\FMEData2018\Data\Orthophotos\08-09-PQ.tif" "C:\FMEData2018\Data\Orthophotos\08-09-RS.tif" "C:\FMEData2018\Data\Orthophotos\10-11-HI.tif" "C:\FMEData2018\Data\Orthophotos\10-11-JK.tif" "C:\FMEData2018\Data\Orthophotos\10-11-LM.tif" "C:\FMEData2018\Data\Orthophotos\10-11-NO.tif" "C:\FMEData2018\Data\Orthophotos\10-11-PQ.tif" "C:\FMEData2018\Data\Orthophotos\10-11-RS.tif" "C:\FMEData2018\Data\Orthophotos\12-13-HI.tif" "C:\FMEData2018\Data\Orthophotos\12-13-JK.tif" "C:\FMEData2018\Data\Orthophotos\12-13-LM.tif" "C:\FMEData2018\Data\Orthophotos\12-13-NO.tif" "C:\FMEData2018\Data\Orthophotos\12-13-PQ.tif" "C:\FMEData2018\Data\Orthophotos\12-13-RS.tif" "C:\FMEData2018\Data\Orthophotos\14-15-HI.tif" "C:\FMEData2018\Data\Orthophotos\14-15-JK.tif" "C:\FMEData2018\Data\Orthophotos\14-15-LM.tif" "C:\FMEData2018\Data\Orthophotos\14-15-NO.tif" "C:\FMEData2018\Data\Orthophotos\14-15-PQ.tif" "C:\FMEData2018\Data\Orthophotos\14-15-RS.tif""
- DGNV8_1: DGNV8 from C:\FMEData2018\Data\Transportation\RoadsDGN.dgn

Writers:
- JPEG_2: JPEG to C:\FMEData2018\Output
- GENERIC_1: GENERIC to C:\FMEData2018\Output in $(OutputCoordSys)

Note: DGN Reader feature type (Roads)
Arterial (reader DGNV8_1)
    -> VectorOnRasterOverlayer [VECTOR]
Note: GeoTIFF Reader feature type (Orthophotos)
06_07_LM (reader GEOTIFF_1)
    -> RasterResampler
RasterResampler
    INTERPOLATION_TYPE_NAME = Nearest Neighbor
    ROWCOL_OR_CELLSIZE = CellSize
    X_CELL_SIZE = $(CellSpacing)
    Y_CELL_SIZE = $(CellSpacing)
    RESAMPLED -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> VectorOnRasterOverlayer [RASTER]
VectorOnRasterOverlayer
    ALPHA = 1.0
    ANTI_ALIASING = No
    ATTR_ACCUM_MODE = Merge Vectors
    ATTR_CONFLICT_RES = Use Raster
    COMPOSITE_USING_ALPHA_BAND = No
    TOLERANCE = 0.5
    RASTER -> 06_07_LM (writer GENERIC_1)
Note: Generic Writer feature type
06_07_LM (writer GENERIC_1)
Note: JPEG Writer feature type
06_07_LM (writer JPEG_2)
