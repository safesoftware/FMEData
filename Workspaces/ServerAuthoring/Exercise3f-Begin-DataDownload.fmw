FME workspace Exercise3f-Begin-DataDownload.fmw

Parameters:
- SourceDataset_GEOTIFF = ""C:\FMEData2015\Data\Orthophotos\06-07-LM.tif" "C:\FMEData2015\Data\Orthophotos\06-07-NO.tif""   # Source GeoTIFF File(s)
- Resolution = 5   # Image Resolution (1-50)
- Format = ECW
- CoordinateSystem = UTM83-10
- FEATURE_TYPES = Arterial   # Feature Types to Read

Readers:
- GEOTIFF_1: GEOTIFF from $(SourceDataset_GEOTIFF)
- DGNV8_1: DGNV8 from C:\FMEData2015\Data\Transportation\RoadsDGN.dgn

Writers:
- GENERIC_1: GENERIC to C:\FMEData2015\Output\Training in $(CoordinateSystem)

GEOTIFF (reader GEOTIFF_1)
    -> RasterResampler
RasterResampler
    INTERPOLATION_TYPE_NAME = Nearest Neighbor
    ROWCOL_OR_CELLSIZE = CellSize
    Y_CELL_SIZE = $(Resolution)
    X_CELL_SIZE = $(Resolution)
    RESAMPLED -> RasterMosaicker
RasterMosaicker
    INTERPOLATION_TYPE_NAME = Nearest Neighbor
    MERGE_PALETTES_NAME = Yes
    COMPOSITE_USING_ALPHA_BAND_NAME = No
    NODATA_OVERWRITE = No
    SNAPPING_TYPE_NAME = Resample
    ACCUM_ATTRS_NAME = Yes
    -> VectorOnRasterOverlayer [input 2]
Note: RoadsDGN [DGNV8]
Other (reader DGNV8_1)
    -> VectorOnRasterOverlayer [input 1]
VectorOnRasterOverlayer
    TOLERANCE = 0.5
    ANTI_ALIASING = No
    COMPOSITE_USING_ALPHA_BAND = No
    ALPHA = 1.0
    RASTER -> AirphotoMosaic (writer GENERIC_1)
AirphotoMosaic (writer GENERIC_1)
