FME workspace what-are-list-attributes.fmw

Parameters:
- SourceDataset_JSON = https://s3.amazonaws.com/FMEData/FMEData/Resources/FormBasic/fruit.json   # Source JSON (JavaScript Object Notation) File or URL
- SourceDataset_JSON_5 = https://s3.amazonaws.com/FMEData/FMEData/Resources/FormBasic/fruit-nested.json   # Source JSON (JavaScript Object Notation) File or URL

Readers:
- JSON_3: JSON from $(SourceDataset_JSON)
- JSON_2: JSON from $(SourceDataset_JSON_5)

Note: How would you get a feature per fruit and per field?
Note: Example feature: / Attribute(string: UTF-8) : `fields' has value `north' / Attribute(string: UTF-8) : `name' has value `Apple' / Attribute(string: UTF-8) : `scientificName' has value `Malus domestica'

Bookmark: Data as flat JSON
Creator
    GEOMTYPE = No Geometry
    NUM = 1
    CREATED -> JSONFormatter
Note: [ / { / "name" : "Apple", / "scientificName" : "Malus domestica" / }, / { / "name" : "Orange", / "scientificName" : "Citrus X sinensis" / }, / { / "name" : "Pear", / "scientificName" : "Pyrus" / } / ]
JSONFormatter
    ERROR_LIST_ATTR = _json_error
    FILEPATH_OR_URL = https://s3.amazonaws.com/FMEData/FMEData/Resources/FormBasic/fruit.json
    FORMAT_LOOKUP = PRETTY_PRINT
    INDENT_SIZE = 3
    INPUT_PORT_CONNECTED = CONNECTED
    OUTPUT_ATTR = _formatted
    OUTPUT_ENCODING = UTF-8
    READ_FROM_FILE = YES
    REMOVE_EMPTY_OBJECTS_AND_ARRAYS_LOOKUP = NO
    REMOVE_EMPTY_STRINGS_LOOKUP = NO
    REMOVE_NULLS_LOOKUP = NO
    FORMAT = Pretty Print
    INDENT_STYLE = 3 spaces
    REMOVE_EMPTY_OBJECTS_AND_ARRAYS = No
    REMOVE_EMPTY_STRINGS = No
    REMOVE_NULLS = No

Bookmark: JSON as features, building a list, exploding a list
Note: Reading JSON as features using JSON reader / name scientificName / Apple Malus domestica / Orange Citrus X sinensis / Pear Pyrus
JSONFeature (reader JSON_3)
    attributes: name string, scientificName string
    -> ListBuilder
Note: Attribute(string: UTF-8) : `_fruit{0}.name' has value `Apple' / Attribute(string: UTF-8) : `_fruit{0}.scientificName' has value `Malus domestica' / Attribute(string: UTF-8) : `_fruit{1}.name' has value `Orange' / Attribute(string: UTF-8) : `_fruit{1}.scientificName' has value `Citrus X sinensis' / Attribute(string: UTF-8) : `_fruit{2}.name' has value `Pear' / Attribute(string: UTF-8) : `_fruit{2}.scientificName' has value `Pyrus'
ListBuilder
    LIST_ATTRS_TO_INCLUDE = name scientificName
    LIST_NAME = fruit
    -> ListExploder
Note: Back to features
ListExploder
    ATTR_CONFLICT_RES_LOOKUP = INCOMING_IF_CONFLICT
    LIST_ATTR = fruit{}
    ATTR_ACCUM_MODE = Merge List Attributes
    ATTR_CONFLICT_RES = Use List Attribute Values

Bookmark: Data as nested JSON
Creator_2
    GEOMTYPE = No Geometry
    NUM = 1
    CREATED -> JSONFormatter_2
Note: { / "fruits": [ / { / "name": "Apple", / "scientificName": "Malus domestica", / "fields": [ / "north", / "south" / ] / }, / { / "name": "Orange", / "scientificName": "Citrus X sinensis", / "fields": [ / "north", / "east" / ] / }, / { / "name": "Pear", / "scientificName": "Pyrus", / "fields": [ / "west", / "south" / ] / } / ] / }
JSONFormatter_2
    ERROR_LIST_ATTR = _json_error
    FILEPATH_OR_URL = https://s3.amazonaws.com/FMEData/FMEData/Resources/FormBasic/fruit-nested.json
    FORMAT_LOOKUP = PRETTY_PRINT
    INDENT_SIZE = 3
    INPUT_PORT_CONNECTED = CONNECTED
    OUTPUT_ATTR = _formatted
    OUTPUT_ENCODING = UTF-8
    READ_FROM_FILE = YES
    REMOVE_EMPTY_OBJECTS_AND_ARRAYS_LOOKUP = NO
    REMOVE_EMPTY_STRINGS_LOOKUP = NO
    REMOVE_NULLS_LOOKUP = NO
    FORMAT = Pretty Print
    INDENT_STYLE = 3 spaces
    REMOVE_EMPTY_OBJECTS_AND_ARRAYS = No
    REMOVE_EMPTY_STRINGS = No
    REMOVE_NULLS = No

Bookmark: Reading nested JSON, exploding to features, list still present
JSONFeature (reader JSON_2)
    attributes: fruits{}.name string, fruits{}.scientificName string, fruits{}.fields{} string
    -> ListExploder_2
ListExploder_2
    ATTR_CONFLICT_RES_LOOKUP = INCOMING_IF_CONFLICT
    LIST_ATTR = fruits{}
    ATTR_ACCUM_MODE = Merge List Attributes
    ATTR_CONFLICT_RES = Use List Attribute Values
