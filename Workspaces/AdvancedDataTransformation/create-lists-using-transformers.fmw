FME workspace create-lists-using-transformers.fmw
Title: Park_Trees

Parameters:
- SourceDataset_CSV2 = https://s3.amazonaws.com/FMEData/FMEData/Resources/FormBasic/street-trees.csv   # Source CSV (Comma Separated Value) File(s)
- SourceDataset_GEOJSON = https://s3.amazonaws.com/FMEData/FMEData/Resources/FormBasic/parks-polygon-representation.geojson   # Source GeoJSON File or URL

Readers:
- CSV2_2: CSV2 from $(SourceDataset_CSV2)
- GEOJSON_2: GEOJSON from $(SourceDataset_GEOJSON)

Note: City of Vancouver - Open Data Portal : / Street Trees
Note: City of Vancouver - Open Data Portal : / Park Polygons
parks-polygon-representation (reader GEOJSON_2)
    attributes: park_name string, park_id float, area_ha float, park_url string
    -> PointOnAreaOverlayer [AREA]
Note: Overlay the trees and the parks to see which parks contain trees.
PointOnAreaOverlayer
    DEAGGREGATE_INPUT = Yes
    OV_ATTR = _overlaps
    POLYS_FIRST = NO

Bookmark: Street Trees
CSV (reader CSV2_2)
    attributes: TREE_ID uint32, CIVIC_NUMBER uint32, STD_STREET varchar(20), GENUS_NAME varchar(14), SPECIES_NAME varchar(18), CULTIVAR_NAME varchar(20), COMMON_NAME varchar(30), ASSIGNED varchar(1), ROOT_BARRIER varchar(1), PLANT_AREA varchar(2), ON_STREET_BLOCK uint32, ON_STREET varchar(20), NEIGHBOURHOOD_NAME varchar(24), STREET_SIDE_NAME varchar(4), HEIGHT_RANGE_ID uint32, DIAMETER real32, CURB varchar(1), DATE_PLANTED date, Geom varchar(58)
    -> GeometryReplacer
Note: Interpret GeoJSON geometry field
GeometryReplacer
    KIND = GEOJSON
    REMOVE_ATTRIBUTE = Yes
    SOURCE = @Value(Geom)
    KIND_LONG = GeoJSON
    -> CoordinateSystemSetter
CoordinateSystemSetter
    COORDSYS = LL-WGS84
    -> AttributeValueMapper
Note: Map HEIGHT_RANGE_ID to HEIGHT_RANGE / 0-10 for every 10 feet / (e.g., 0 = 0-10 ft, 1 = 10-20 ft, 2 = 20-30 ft, and 10 = 100+ ft)
AttributeValueMapper
    LUT = 0,0-10,1,10-20,2,20-30,3,30-40,4,40-50,5,50-60,6,60-70,7,70-80,8,80-90,9,90-100,10,100-110,11,110-120
    MAPPING_DIRECTION = FORWARD
    SRC = HEIGHT_RANGE_ID
    VAL_ATTR = HEIGHT_RANGE
    -> AttributeValueMapper_2
Note: Map HEIGHT_RANGE_ID to HEIGHT / 0-10 for every 10 feet / (e.g., 0 = 5 ft, 1 = 15 ft, 2 = 25 ft, and10 = 105+ ft)
AttributeValueMapper_2
    LUT = 0,5,1,15,2,25,3,35,4,45,5,55,6,65,7,75,8,85,9,95,10,105,11,115
    MAPPING_DIRECTION = FORWARD
    SRC = HEIGHT_RANGE_ID
    VAL_ATTR = HEIGHT
    -> PointOnAreaOverlayer [POINT]
