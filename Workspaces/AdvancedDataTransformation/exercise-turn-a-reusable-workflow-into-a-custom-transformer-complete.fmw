FME workspace exercise-turn-a-reusable-workflow-into-a-custom-transformer-complete.fmw

Parameters:
- SourceDataset_OGCKML = https://s3.amazonaws.com/FMEData/FMEData/Data/Boundaries/VancouverNeighborhoods.kml   # Source Google KML File or URL

Readers:
- OGCKML_1: OGCKML from $(SourceDataset_OGCKML)

Neighborhoods (reader OGCKML_1)
    attributes: NeighborhoodId kml_buffer, NeighborhoodName kml_buffer, NeighborhoodURL kml_buffer, TotalPopulation2001 kml_buffer, TotalPopulation2011 kml_buffer
    -> AttributeRemover
Note: Remove ID and URL
AttributeRemover
    REMOVE_ATTRS = NeighborhoodId,NeighborhoodURL
    -> CsmapReprojector
Note: Reproject to UTM83-10
CsmapReprojector
    DEST = UTM83-10
    INTERPOLATION_TYPE_NAME = NearestNeighbor
    RASTER_CELL_SIZE = PreserveCells
    RASTER_TOLERANCE = 0.0
    REPROJECTED -> DensityEvaluator [AreaCalculator_Input]
DensityEvaluator
    TOTALPOPULATION2001 = @Value(TotalPopulation2001)
    ExpressionEvaluator_2001_Output -> ExpressionEvaluator_2011
ExpressionEvaluator_2011
    ACTION = Create New Attribute
    EXPRESSION = @Value(TotalPopulation2011)/@Value(NeighborhoodArea)
    VAL_ATTR = PopulationDensity2011
    -> Output
Output: Inspector

FME custom transformer DensityEvaluator
A transformer to calculate the density of attribute values in a specific area.

Parameters:
- TOTALPOPULATION2001 = @Value(TotalPopulation2001)   # TotalPopulation2001

AreaCalculator_Input (input)
    -> AreaCalculator
Note: Calculate Area in SQ KM
AreaCalculator
    AREA_ATTR = NeighborhoodArea
    AREA_TYPE = Plane Area
    MULT = .000001
    -> ExpressionEvaluator_2001
ExpressionEvaluator_2001
    ACTION = Create New Attribute
    EXPRESSION = @Value(TotalPopulation2001)/@Value(NeighborhoodArea)
    VAL_ATTR = PopulationDensity2001
    -> ExpressionEvaluator_2001_Output (output)
ExpressionEvaluator_2001_Output (output)
