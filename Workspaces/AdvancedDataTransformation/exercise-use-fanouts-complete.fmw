FME workspace exercise-use-fanouts-complete.fmw

Parameters:
- FEATURE_TYPES = GarbageSchedule Libraries Parks
- DestDataset_GENERIC = C:\FMEData\Output\Training   # Destination Generic (Any Format) Folder
- OutputFormat = ESRISHAPE

Readers:
- FILEGDB_1: FILEGDB from https://s3.amazonaws.com/FMEData/FMEData/Data/CommunityMapping/CommunityMap.gdb.zip

Writers:
- GENERIC_1: GENERIC to $(DestDataset_GENERIC)

FoodVendors (reader FILEGDB_1)
    attributes: VendorID smallint, VendorName text(48), VendorDescription text(16), OBJECTID objectid, Subzone text(30), LibraryID text(6), ParkURL text(100), CentreName text(30), LibraryURL text(80), CentreURL text(50), Schedule text(30), LibraryName text(30), StationName text(30), Description text(75), Zone text(30), BookCount int, ParkName text(30), Regulation text(75), FountainID smallint, LibraryAddress text(30), Circulation int, ParkAddress text(50), Location text(50), CentreAddress text(30), NumAddresses smallint, UserVisits int, Maintainer text(16)
    -> Tiler
Tiler
    CLEANING_TOLERANCE_LOOKUP = AUTO
    COLUMN_ATTR = _column
    DUPLICATE_ON_TILE_BORDERS = NO
    INVALID_PART_HANDLING = REJECT_WHOLE_FEATURE
    MISSING_MEASURE_VALUES_LOOKUP = LINEAR_INTERPOLATION
    MISSING_Z_VALUES_LOOKUP = PLANAR_INTERPOLATION
    NUM_HORIZONTAL_TILES = 2
    NUM_VERTICAL_TILES = 2
    ROW_ATTR = _row
    STARTINGCORNER = BOTTOM_LEFT
    TILING_TYPE = NUM_TILES
    CLEANING_TOLERANCE = Automatic
    MISSING_MEASURE_VALUES = Linear Interpolation
    MISSING_Z_VALUES = Planar Interpolation
    TILED -> NewFeatureType (writer GENERIC_1)
NewFeatureType (writer GENERIC_1)
    attributes: VendorID int16, VendorName varchar(48), VendorDescription varchar(16), OBJECTID int32, Subzone varchar(30), LibraryID varchar(6), ParkURL varchar(100), CentreName varchar(30), LibraryURL varchar(80), CentreURL varchar(50), Schedule varchar(30), LibraryName varchar(30), StationName varchar(30), Description varchar(75), Zone varchar(30), BookCount int32, ParkName varchar(30), Regulation varchar(75), FountainID int16, LibraryAddress varchar(30), Circulation int32, ParkAddress varchar(50), Location varchar(50), CentreAddress varchar(30), NumAddresses int16, UserVisits int32, Maintainer varchar(16), _column uint32, _row uint32
