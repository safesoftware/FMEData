FME workspace exercise-use-conditional-filtering-complete.fmw

Parameters:
- SourceDataset_MITAB = https://s3.amazonaws.com/FMEData/FMEData/Data/Parks.zip   # Source MapInfo TAB File(s)
- DestDataset_MITAB = C:\FMEData\Output\Training   # Destination MapInfo Folder

Readers:
- MITAB_1: MITAB from $(SourceDataset_MITAB)

Writers:
- MITAB_2: MITAB to $(DestDataset_MITAB)

AttributeManager
    ATTR_TABLE = RENAME_SET_VALUE NeighborhoodName > Neighborhood (varchar(40))
    -> Tester
Tester
    BOOL_OP = OR
    TEST_CLAUSE = TEST @Value(DogPark) = N
    TEST_MODE = TEST
    PASSED -> ParksMaintenanceData (writer MITAB_2)
    FAILED -> Tester_Failed
Tester_Failed: Logger
    LOG_FEATURE = LOG_ONLY
    MAXCOORDS = 20
    MAXFEATS = 20
    MESSAGE = Feature is:
    SEVERITY = INFO

Bookmark: Reader Feature Types
Parks (reader MITAB_1)
    attributes: ParkId smallint, RefParkId smallint, ParkName char(40), NeighborhoodName char(40), VisitorCount smallint, TreeCount smallint, DogPark char(1), Washrooms char(1), SpecialFeatures char(1)
    -> AttributeManager

Bookmark: Writer Feature Types
ParksMaintenanceData (writer MITAB_2)
    attributes: ParkId smallint, ParkName char(40), Neighborhood char(40), VisitorCount integer, TreeCount smallint, ParkArea float, AverageParkArea float
