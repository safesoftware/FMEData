FME workspace choose-a-join-transformer.fmw

Readers:
- ACAD_2: ACAD from https://s3.amazonaws.com/FMEData/FMEData/Data/Transportation/CompleteRoads.dwg
- XLSXR_2: XLSXR from https://s3.amazonaws.com/FMEData/FMEData/Data/Transportation/Snowfall.xlsx

Note: What joining transformer should Fatima use in each case to get the result described?
Note: CompleteRoads [ACAD]
Private (reader ACAD_2)
    attributes: From_HBlock number(4,0), OneWay char(1), StreetId number(5,0), StreetName char(19)
Note: Snowfall [XLSXR]
Snowfall (reader XLSXR_2)
    attributes: StreetId number(5,0), EstimatedSnowfall number(3,0), Temperature number(4,1), WeatherStation number(1,0), LastTreated number(2,0), RoadType char(11)
FeatureMerger
    ATTR_ACCUM_MODE = Merge Supplier
    ATTR_CONFLICT_RES_LOOKUP = REQUESTOR_IF_CONFLICT
    IGNORE_NULLS = No
    JOIN_KEYS = @Value(StreetId) @Value(StreetId) AUTO
    MERGE_TYPE_VAL = ATTRIBUTES
    PROCESS_DUPS = NO
    REJECT_NULL_MISSING_KEYS = Yes
    SUPPLIERS_FIRST = No
    ATTR_CONFLICT_RES = Use Requestor
    MERGE_TYPE = Merge Attributes
InlineQuerier
    QUERY_DEF:
      Joined,SELECT Roads."Roads.fme_feature_content", Snowfall."EstimatedSnowfall", Snowfall."LastTreated", Snowfall."RoadType", Snowfall."Temperature", Snowfall."WeatherStation"
      FROM Roads
      INNER JOIN Snowfall ON Roads.StreetId=Snowfall.StreetId;,FIRST
    TABLE_DEF = Roads,From_HBlock,integer,OneWay,varchar(2),StreetId,integer,StreetName,varchar(20),HBlock,varchar(28),fme_feature_type,varchar(50),Snowfall,StreetId,integer,EstimatedSnowfall,integer,Temperature,"real(4,1)",WeatherStation,integer,LastTreated,integer,RoadType,varchar(12)
DatabaseJoiner
    ADDED_FIELDS = EstimatedSnowfall LastTreated RoadType Temperature WeatherStation
    ATTR_CONFLICT_RES_LOOKUP = PREFER_ORIGINAL
    DATASET = https://s3.amazonaws.com/FMEData/FMEData/Data/Transportation/Snowfall.xlsx
    FORMAT = XLSXR
    JOIN_KEYS = StreetId StreetId
    LIST_MULTIPLE_RESULTS = NO
    MATCH_RULE = MATCH_ALL
    TABLE = Snowfall
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_EXPOSED_ATTRS = xlsx_row_id,number(11,0)
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    ATTR_ACCUM_MODE = Merge Joined
    ATTR_CONFLICT_RES = Use Original
    MATCH_MULTIPLE_DISPLAY = Create a feature for each match
    MATCH_RULE_DISPLAY = Match All (1:M)
FeatureJoiner
    ATTR_CONFLICT_RES = USE_LEFT
    GEOMETRY_HANDLING = USE_LEFT
    JOIN_KEYS = StreetId StreetId AUTO
    JOIN_MODE = Inner

Bookmark: Use Case 1
Note: 3,995 road segments joined to add the EstimatedSnowfall using Snowfall as an external table (i.e., not the feature type in this workspace).

Bookmark: Use Case 2
Note: 3,995 road segments joined to add the EstimatedSnowfall attribute, rejecting null and missing keys.

Bookmark: Use Case 3
Note: 3,995 road segments joined to add the EstimatedSnowfall attribute using an SQL-style inner join.

Bookmark: Use Case 4
Note: 3,995 road segments joined to add the EstimatedSnowfall attribute using SQL.
