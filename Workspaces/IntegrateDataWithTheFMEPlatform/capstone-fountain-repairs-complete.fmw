FME workspace capstone-fountain-repairs-complete.fmw
Title: Fountain repair list
Description: Capstone model answer: join inspections to drinking fountains
 add new fountains from coordinates
 keep the ones that need repair
 and write GeoJSON.

Parameters:
- DestDataset_GEOJSON = C:\FMEData\Output\Training\fountain-repairs.geojson   # Destination GeoJSON File

Readers:
- OPENFILEGDB_1: OPENFILEGDB from https://s3.amazonaws.com/FMEData/FMEData/Data/CommunityMapping/CommunityMap.gdb.zip

Writers:
- GEOJSON_1: GEOJSON to $(DestDataset_GEOJSON)

Bookmark: Read
Note: Read the two sources. / DrinkingFountains comes from CommunityMap.gdb: 113 points in UTM83-10. / The inspection records are JSON on the web, so HTTPCaller downloads FountainInspections.json into _response_body. JSONFragmenter splits it with the query json["inspections"][*], giving one feature per inspection and flattening nested keys to names like fountain.id and result.status. AttributeExposer then exposes those attributes so the transformers downstream can use them.
HTTPCaller
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://s3.amazonaws.com/FMEData/FMEData/Data/CommunityMapping/FountainInspections.json
    TRANSFER_TIMEOUT_LENGTH = 90
    USE_COOKIES = No
    VERIFY_SSL_CERTIFICATES = Yes
    -> JSONFragmenter
JSONFragmenter
    EXPLODE_FORMAT = JSON
    EXTRACT_ATTR = Yes
    INPUT_PORT_CONNECTED = CONNECTED
    JSON_ATTR = _response_body
    JSON_QUERY = json["inspections"][*]
    READ_FROM_FILE = NO
    RECURSIVE = YES
    REJECT_EMPTY_LISTS = YES
    FRAGMENTS -> AttributeExposer
AttributeExposer
    ATTR_TABLE = _creation_instance,uint8,_http_status_code,uint8,_response_body,buffer,json_index,uint8,json_type,varchar(6),fountain.id,uint8,fountain.location,buffer,fountain.maintainer,buffer,fountain.longitude,real64,fountain.latitude,real64,inspected_on,buffer,result.status,buffer,result.notes,buffer
    -> FeatureJoiner [RIGHT]
DrinkingFountains (reader OPENFILEGDB_1)
    attributes: FountainID smallint, Location text(48), Maintainer text(16), OBJECTID largeint
    -> FeatureJoiner [LEFT]

Bookmark: Join
Note: Join each inspection to its fountain on FountainID = fountain.id. / FeatureJoiner (Inner) keeps the Left geometry, so joined features take the fountain's point from the geodatabase, along with its Location and Maintainer. / UnjoinedLeft: fountains nobody inspected (8). They are not needed. / UnjoinedRight: inspections with no matching fountain (5). These are the new fountains.
FeatureJoiner
    ATTR_CONFLICT_RES = USE_LEFT
    GEOMETRY_HANDLING = USE_LEFT
    JOIN_KEYS = FountainID fountain.id AUTO
    JOIN_MODE = Inner
    JOINED -> AttributeFilter
    UNJOINED_RIGHT -> VertexCreator

Bookmark: New fountains
Note: New fountains are not in the geodatabase, so there is no point to join to. / VertexCreator builds each point from fountain.longitude and fountain.latitude and sets the coordinate system to LL84. AttributeManager then renames their attributes to match the joined fountains (FountainID, Location, Maintainer), so both streams line up.
VertexCreator
    COORDSYS = LL84
    MEASURE_TYPE_LOOKUP = CONTINUOUS
    MODE = REPLACE
    REMOVE_ATTRIBUTES = No
    XVAL = @Value(fountain.longitude)
    YVAL = @Value(fountain.latitude)
    MEASURE_TYPE = Continuous
    MODE_NAME = Replace with Point
    -> AttributeManager_NewFountains
AttributeManager_NewFountains
    ATTR_TABLE:
      RENAME_SET_VALUE fountain.id > FountainID (uint8)
      RENAME_SET_VALUE fountain.location > Location (buffer)
      RENAME_SET_VALUE fountain.maintainer > Maintainer (buffer)
      REMOVE fountain.longitude (real64)
      REMOVE fountain.latitude (real64)
    -> AttributeFilter

Bookmark: Filter
Note: Merge both streams into one AttributeFilter on result.status. / Only the Needs Repair and Out of Service ports are connected. OK inspections stop here.
AttributeFilter
    ATTR_NAME = result.status
    ATTR_VALUES = <Empty>,<Missing>,<Null>,<Unfiltered>,Needs Repair,OK,Out of Service
    Needs Repair -> AttributeManager_OutputSchema
    Out of Service -> AttributeManager_OutputSchema

Bookmark: Output schema
Note: Set the output schema and write GeoJSON. / AttributeManager leaves exactly five attributes: fountain_id, location, maintainer, status, inspected_on. / The GeoJSON writer's Reproject to WGS84 parameter (Yes by default) converts every feature from its own coordinate system, so the UTM83-10 fountains and the LL84 new fountains both come out as longitude/latitude. No Reprojector is needed.
AttributeManager_OutputSchema
    ATTR_TABLE:
      RENAME_SET_VALUE FountainID > fountain_id (int16)
      RENAME_SET_VALUE Location > location (varchar(48))
      RENAME_SET_VALUE Maintainer > maintainer (varchar(16))
      RENAME_SET_VALUE result.status > status (buffer)
      REMOVE OBJECTID (int64)
      REMOVE _creation_instance (uint64)
      REMOVE _response_body (buffer)
      REMOVE _http_status_code (buffer)
      REMOVE json_type (buffer)
      REMOVE json_index (uint32)
      REMOVE fountain.id (uint8)
      REMOVE fountain.location (buffer)
      REMOVE fountain.maintainer (buffer)
      REMOVE fountain.longitude (real64)
      REMOVE fountain.latitude (real64)
      REMOVE result.notes (buffer)
    -> fountain-repairs (writer GEOJSON_1)
fountain-repairs (writer GEOJSON_1)
    attributes: fountain_id int, location string, maintainer string, status string, inspected_on string
