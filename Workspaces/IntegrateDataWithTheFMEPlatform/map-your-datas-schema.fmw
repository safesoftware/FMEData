FME workspace map-your-datas-schema.fmw

Parameters:
- SourceDataset_POSTGIS = FME Training PostGIS Database   # Connection
- DestDataset_FILEGDB = C:\FMEData2020\Output\Training\BusinessOwners.gdb   # File Geodatabase

Readers:
- POSTGIS_1: POSTGIS from $(SourceDataset_POSTGIS)

Writers:
- FILEGDB_1: FILEGDB to $(DestDataset_FILEGDB)

GeometryFilter
    BREAK_AGG = Yes
    GEOM_PORT_NAMES = Point Line Area Surface Collection Null
    INSTANTIATE = Yes
    POINT -> BusinessOwners (writer FILEGDB_1)
    COLLECTION -> BusinessOwners_incomplete (writer FILEGDB_1)
    NULL -> BusinessOwners_incomplete (writer FILEGDB_1)

Bookmark: Reader Feature Types
BusinessOwners (reader POSTGIS_1)
    attributes: first varchar(12), last_name varchar(11), company varchar(41), license_number varchar(7), longitude float8, latitude float8
    -> GeometryFilter

Bookmark: Writer Feature Types
BusinessOwners (writer FILEGDB_1)
    attributes: last_name text(11), first_name text(12), company text(41), license_number text(7)
BusinessOwners_incomplete (writer FILEGDB_1)
    attributes: first text(12), last_name text(11), company text(41), license_number text(7), longitude double, latitude double
