FME workspace view-information-about-a-specific-feature.fmw
Title: BuildingFootprints
Description: Extrude building footprints and compare to point cloud

Parameters:
- SourceDataset_SPATIALITE = https://s3.amazonaws.com/FMEData/FMEData/Data/Engineering/BuildingFootprints/building_footprints.sl3   # SpatiaLite Database
- SourceDataset_LAS = https://s3.amazonaws.com/FMEData/FMEData/Data/PointClouds/CoV_4910E_54580N.laz   # Source ASPRS LAS File(s)

Readers:
- SPATIALITE_1: SPATIALITE from $(SourceDataset_SPATIALITE)
- LAS_1: LAS from $(SourceDataset_LAS) in UTM83-10

Note: City of Vancouver point cloud
LAS (reader LAS_1)
    -> BoundingBoxReplacer
    -> Clipper [CANDIDATE]
Note: Extrude to avght_m
Extruder
    DIRECTION_LOOKUP = AUTO
    DISTANCE = @Value(avght_m)
    DIRECTION = Auto

Bookmark: Point Cloud
BoundingBoxReplacer
    BBTYPE = BB
    BOXTYPE = 2D Bounding Box
    BOX -> Scaler
Scaler
    DISABLE_FACTORIES = *
    RASTER_SCALING = Extents
    TEXT_LOC_ONLY = Location and Size
    XSCALE = .55
    YSCALE = .55
    ZSCALE = 1
    SCALE_ORIGIN = Center Point
    SCALED -> Clipper [CLIPPER]
Note: Clip to area of interest
Clipper
    ADD_NODATA = NO
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_PARTS
    MISSING_M_MODE_LOOKUP = LINEAR
    MISSING_Z_MODE_LOOKUP = LINEAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Linear Interpolation
    INSIDE -> GeometryFilter
GeometryFilter
    FILTER_MODE = SIMPLE
    FILTER_MULTI = FILTER_TYPES]Area]FME_CONTROLLER_QUERY_FILE]]FME_CONTROLLER_CHOICE]Simple
    Area -> Extruder

Bookmark: Building Footprints
building_footprints (reader SPATIALITE_1)
    attributes: id real(20,10), orient8 real(20,10), bldgid integer64, topelev_m real(20,10), med_slope integer64, baseelev_m real(20,10), hgt_agl real(20,10), rooftype string(254), area_m2 real(20,10), avght_m real(20,10), minht_m real(20,10), maxht_m real(20,10), base_m real(20,10), len real(20,10), wid real(20,10)
    -> 3DForcer
Note: Set base as base_m
3DForcer
    KEEPZVAL = No
    ZVALATTR = @Value(base_m)
    -> Clipper [CANDIDATE]
