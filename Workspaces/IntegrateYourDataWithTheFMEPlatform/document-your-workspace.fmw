FME workspace document-your-workspace.fmw

Parameters:
- SourceDataset_XLSXR = https://s3.amazonaws.com/FMEData/FMEData2020/Data/Planning/BusinessOwners.xlsx   # Source Microsoft Excel File(s)
- SourceDataset_XLSXR_3 = https://s3.amazonaws.com/FMEData/FMEData2020/Data/Culture/PublicArt.xlsx   # Source Microsoft Excel File(s)
- DestDataset_FILEGDB = C:\FMEData2020\Output\Training\Vancouver.gdb   # File Geodatabase

Readers:
- XLSXR_1: XLSXR from $(SourceDataset_XLSXR) in LL84
- XLSXR_2: XLSXR from $(SourceDataset_XLSXR_3) in LL84

Writers:
- FILEGDB_1: FILEGDB to $(DestDataset_FILEGDB)

BusinessOwners (reader XLSXR_1)
    attributes: First char(12), Last Name char(11), Company char(41), License Number char(7), Longitude x_coordinate, Latitude y_coordinate
    -> BusinessOwners (writer FILEGDB_1)
BusinessOwners (writer FILEGDB_1)
    attributes: First text(12), Last_Name text(11), Company text(41), License_Number text(7), Longitude double, Latitude double
Downtown (reader XLSXR_2)
    attributes: Name char(51), Title char(51), Longitude x_coordinate, Latitude y_coordinate
    -> PublicArt (writer FILEGDB_1)
Mount Pleasant (reader XLSXR_2)
    attributes: Name char(46), Title char(32), Longitude x_coordinate, Latitude y_coordinate
    -> PublicArt (writer FILEGDB_1)
Strathcona (reader XLSXR_2)
    attributes: Name char(45), Title char(33), Longitude x_coordinate, Latitude y_coordinate
    -> PublicArt (writer FILEGDB_1)
Fairview (reader XLSXR_2)
    attributes: Name char(27), Title char(50), Longitude x_coordinate, Latitude y_coordinate
    -> PublicArt (writer FILEGDB_1)
Kitsilano (reader XLSXR_2)
    attributes: Name char(41), Title char(51), Longitude x_coordinate, Latitude y_coordinate
    -> PublicArt (writer FILEGDB_1)
West End (reader XLSXR_2)
    attributes: Name char(26), Title char(35), Longitude x_coordinate, Latitude y_coordinate
    -> PublicArt (writer FILEGDB_1)
PublicArt (writer FILEGDB_1)
    attributes: Name text(51), Title text(51), Longitude double, Latitude double
