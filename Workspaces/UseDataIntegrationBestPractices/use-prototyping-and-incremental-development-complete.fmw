FME workspace use-prototyping-and-incremental-development-complete.fmw
Title: MULTI to MULTI

Readers:
- SHAPEFILE_2: SHAPEFILE from c:\FMEData\Resources\FMEAccelerator\data\road-ahead-upcoming-projects.zip
- CSV2_3: CSV2 from c:\FMEData\Resources\FMEAccelerator\data\business-licences.zip
- CSV2_1: CSV2 from c:\FMEData\Resources\FMEAccelerator\data\food-vendors.csv
- SQLITE3_1: SQLITE3 from C:\FMEData\Data\Planning\business-licences-sqlite.zip

Writers:
- XLSXW_2: XLSXW to c:\FMEData\Output\Training\AffectedVendors.xlsx

CSV (reader CSV2_3)
    attributes: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

Bookmark: Source Data
Note: Upcoming road construction projects (SHP)
road-ahead-upcoming-projects (reader SHAPEFILE_2)
    attributes: project varchar(255), street varchar(255), location varchar(255), comp_date date, url_link varchar(255)
    -> Bufferer
Note: Food Vendors CSV
CSV (reader CSV2_1)
    attributes: KEY varchar(4), VENDOR_TYPE varchar(11), STATUS varchar(4), BUSINESS_NAME varchar(28), LOCATION varchar(75), DESCRIPTION varchar(34), GEO_LOCALAREA varchar(24), x real64, y real64
    -> AttributeValidator
Note: Business Licenses SQLite
business-licences (reader SQLITE3_1)
    attributes: FOLDERYEAR integer, LicenceRSN integer, LicenceNumber varchar(10), LicenceRevisionNumber integer, BusinessName varchar(89), BusinessTradeName varchar(77), Status varchar(21), IssuedDate varchar(26), ExpiredDate varchar(11), BusinessType varchar(41), BusinessSubType varchar(35), Unit varchar(11), UnitType varchar(6), House varchar(9), Street varchar(21), City varchar(10), Province varchar(3), Country varchar(3), PostalCode varchar(11), LocalArea varchar(25), NumberofEmployees float, FeePaid integer, ExtractDate varchar(26), Geom varchar(72)
    -> Tester

Bookmark: Determine Impacted Area
Bufferer
    ANGLE = 22.5
    CAP_STYLE_LOOKUP = CAP_ARC
    CORNER_STYLE_LOOKUP = JOIN_ARC
    MODE = AREA
    OFFSET = 50
    OFFSET_UNITS = FEET
    PRECISION = APPROX
    CAP_STYLE = Arc
    CORNER_STYLE = Arc
    BUFFERED -> SpatialFilter [Filter]

Bookmark: Validate Food Truck Data
AttributeValidator
    TABLE = KEY$ATTRIBUTE_UNIQUE$<Unused>/BUSINESS_NAME$ATTRIBUTE_HAS_A_VALUE$<Unused>
    PASSED -> SpatialFilter [Candidate]

Bookmark: Find Impacts
SpatialFilter
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    PASSED -> FeatureJoiner [LEFT]

Bookmark: Get Current License Data
Note: Faster to use a WHERE clause on the reader feature type
Tester
    BOOL_OP = COMPOSITE
    COMPOSITE_TEST = 1 AND 2
    TEST_CLAUSE:
      TEST @Value(FOLDERYEAR) = 21
      TEST @Value(Status) != Gone Out of Business
    TEST_MODE = TEST
    PASSED -> FeatureJoiner [RIGHT]

Bookmark: Join Data and Manage Attributes
FeatureJoiner
    ATTR_CONFLICT_RES = USE_LEFT
    GEOMETRY_HANDLING = USE_LEFT
    JOIN_KEYS = BUSINESS_NAME BusinessTradeName AUTO
    JOIN_MODE = Inner
    JOINED -> AttributeManager
AttributeManager
    ATTR_TABLE:
      RENAME_SET_VALUE BUSINESS_NAME > Business Name (varchar(29))
      REMOVE VENDOR_TYPE (varchar(12))
      RENAME_SET_VALUE DESCRIPTION > Description (varchar(35))
      RENAME_SET_VALUE LOCATION > Location (varchar(76))
      RENAME_SET_VALUE STATUS > Status (varchar(5))
      RENAME_SET_VALUE project > Street Project (char(255))
      RENAME_SET_VALUE street > Street (char(255))
      RENAME_SET_VALUE location > Location (char(255))
      RENAME_SET_VALUE comp_date > Completion Date (date)
      RENAME_SET_VALUE url_link > Project Information Link (char(255))
      REMOVE KEY (varchar(5))
      REMOVE GEO_LOCALAREA (varchar(25))
      REMOVE _predicate (buffer)
      REMOVE FOLDERYEAR (uint32)
      REMOVE LicenceRSN (uint32)
      RENAME_SET_VALUE LicenceNumber > Business License Number (varchar(10))
      REMOVE LicenceRevisionNumber (uint32)
      REMOVE BusinessName (varchar(89))
      REMOVE BusinessTradeName (varchar(77))
      REMOVE Status (varchar(21))
      REMOVE IssuedDate (varchar(26))
      REMOVE ExpiredDate (varchar(11))
      REMOVE BusinessType (varchar(41))
      REMOVE BusinessSubType (varchar(35))
      REMOVE Unit (varchar(11))
      REMOVE UnitType (varchar(6))
      REMOVE House (varchar(9))
      REMOVE Street (varchar(21))
      REMOVE City (varchar(10))
      REMOVE Province (varchar(3))
      REMOVE Country (varchar(3))
      REMOVE PostalCode (varchar(11))
      REMOVE LocalArea (varchar(25))
      REMOVE NumberofEmployees (real32)
      REMOVE FeePaid (uint32)
      REMOVE ExtractDate (varchar(26))
      REMOVE Geom (varchar(72))
      REMOVE x (real64)
      REMOVE y (real64)
    -> AffectedVendors (writer XLSXW_2)

Bookmark: Create a Report in Excel
AffectedVendors (writer XLSXW_2)
    attributes: Business Name string(28), Description string(34), Street Project string(255), Location string(255), Completion Date date(20), Project Information Link string(255), Business License Number string(10)
