FME workspace exercise-improving-workspace-style-complete.fmw
Title: BestPractice-Ex3-Begin

Parameters:
- SourceDataset_CSV2 = https://s3.amazonaws.com/FMEData/FMEData/Data/Emergency/Crime.csv   # Source CSV (Comma Separated Value) File(s)
- SourceDataset_MITAB = https://s3.amazonaws.com/FMEData/FMEData/Data/Parks.zip   # Source MapInfo TAB File(s)

Readers:
- FILEGDB_1: FILEGDB from https://s3.amazonaws.com/FMEData/FMEData/Data/Addresses/Addresses.gdb.zip
- CSV2_1: CSV2 from $(SourceDataset_CSV2)
- MITAB_1: MITAB from $(SourceDataset_MITAB)

Note: Join crime to addresses
FeatureJoiner
    ATTR_CONFLICT_RES = Prefer Left
    GEOMETRY_HANDLING = Prefer Left
    JOIN_KEYS = JoinKey Block AUTO
    JOIN_MODE = Inner
    JOINED -> AttributeValueMapper
Parks (reader MITAB_1)
    attributes: ParkId smallint, RefParkId smallint, ParkName char(40), NeighborhoodName char(40), VisitorCount smallint, TreeCount smallint, DogPark char(1), Washrooms char(1), SpecialFeatures char(1)
    -> NeighborFinder [CANDIDATE]
Note: Calculate distance to parks
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> AttributeRenamer
Note: Rename _distance to ParkDistance
AttributeRenamer
    ATTR_TABLE = RENAME_SET_DEFAULT _distance > ParkDistance
    KEEP_RENAMED_ONLY = no
    MISSING_INPUT_ATTRS = PRESERVE
    -> PointOnAreaOverlayer [POINT]
Note: Merge with noise control areas
PointOnAreaOverlayer
    ATTR_ACCUM_MODE = Merge Incoming
    ATTR_CONFLICT_RES = Use Original
    DEAGGREGATE_INPUT = Yes
    OV_ATTR = _overlaps
    POLYS_FIRST = NO
    POINT -> AttributeValueMapper_2

Bookmark: Addresses GDB
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> AttributeSplitter

Bookmark: Prepare addresses to join
AttributeSplitter
    ATTR_NAME = PSTLADDRESS
    DELIMITER = " "
    DROP_EMPTY_PARTS = NO
    LIST_NAME = _list
    TRIM_TYPE = BOTH
    -> AttributeManager
AttributeManager
    ATTR_TABLE:
      REMOVE OBJECTID (int32)
      REMOVE GlobalID (buffer)
      REMOVE OWNERNM1 (varchar(150))
      REMOVE OWNERNM2 (varchar(150))
      RENAME_SET_VALUE PSTLCITY > City (varchar(100))
      RENAME_SET_VALUE PSTLPROV > Province (varchar(25))
      REMOVE INTSTATE (varchar(5))
      REMOVE INTPSTLCD (varchar(10))
      RENAME_SET_VALUE COUNTRY > Country (varchar(100))
      REMOVE REPRESENT (varchar(14))
      REMOVE STATUS (varchar(9))
      REMOVE LASTUPDATE (datetime)
      REMOVE LASTEDITOR (varchar(50))
      RENAME_SET_VALUE POSTALCODE > PostalCode (varchar(6))
      SET_TO Number (varchar(200)) = @Value(_list{0})
      SET_TO Street (varchar(200)) = @Value(_list{1}) @Value(_list{2}) @Value(_list{3})
    -> StringReplacer
StringReplacer
    CASE = NO
    FIND_TEXT = ..$
    NO_MATCH = _FME_NO_OP_
    REGEXP = YES
    REPLACE_TEXT = XX
    SRC_ATTRS = Number
    -> StringCaseChanger
StringCaseChanger
    ATTRCHOICE = SELECTED
    ATTRLIST = Street
    CHANGE_TYPE = upper
    -> AttributeManager_2
Note: Create JoinKey to merge with Crimes Block
AttributeManager_2
    ATTR_TABLE = SET_TO JoinKey (varchar(200)) = @Trim(@Value(Number) @Value(Street))
    -> FeatureJoiner [LEFT]

Bookmark: Crime CSV
Crime (reader CSV2_1)
    attributes: ID string, Type string, Month string, Block string
    -> FeatureJoiner [RIGHT]

Bookmark: Merge crime data
Note: Set CrimeValue based on crime Type
AttributeValueMapper
    LUT = Commercial BE,10,Mischief Over $5000,8,Mischief Under $5000,2,Thef Of Auto Under $5000,4,Theft From Auto Over $5000,7,Theft From Auto Under $5000,3,Theft Of Auto Over $5000,6
    MAPPING_DIRECTION = FORWARD
    SRC = Type
    VAL_ATTR = CrimeValue
    -> Aggregator
Note: Group by address
Aggregator
    ACCUM_ATTRS_NAME = Drop Incoming Attributes
    AGGREGATE_TYPE = Homogeneous Collection (If Possible)
    GROUP_BY = PSTLADDRESS
    MODE = Geometry - Assemble One Level
    SEP = ,
    SUM = CrimeValue
    AGGREGATE -> CenterPointReplacer
CenterPointReplacer
    POINTTYPE = CENTER
    POINT -> NeighborFinder [BASE]

Bookmark: Planning Geopackage - Noise Control Areas
Creator
    GEOMTYPE = Geometry Object
    NUM = 1
    CREATED -> FeatureReader [INITIATOR]
FeatureReader
    ATTRIBUTES = BusinessImprovementAreas,"AreaID,AreaName,LastUpdated",HistoricAreas,"ZoneID,ZoneName,ZoneCategory,ZoneLocation,ZoneDescription,ZonePoliciesPDF,LastUpdated",NoiseControlAreas,"AreaID,AreaName,AreaDescription,LastUpdated",ViewCones,"ViewID,ViewDescription,LastUpdated"
    ATTR_ACCUM_MODE = Only Use Result
    COMBINE_GEOM = Use Result
    DATASET = https://s3.amazonaws.com/FMEData/FMEData/Data/Planning/PlanningRestrictions.gpkg
    FEATURETYPES = NoiseControlAreas
    FORMAT = GEOPACKAGE
    GEOPACKAGE_ENCODE_FEATURE_TYPE_AND_ATTR_NAMES = YES
    GEOPACKAGE_ENFORCE_FOREIGN_KEY_INTEGRITY = YES
    GEOPACKAGE_EXPOSE_PRIMARY_KEY_ATTRIBUTE = NO
    GEOPACKAGE_OPEN_SINGLE_RASTER_AS_SUBDATASET = YES
    GEOPACKAGE_QUERY_FEATURE_TYPES_FOR_MERGE_FILTERS = Yes
    GEOPACKAGE_READER_REPLACE_INVALID_CHARS = YES
    GEOPACKAGE_READ_BOOLEANS_AS_YES_NO = YES
    GEOPACKAGE_READ_NULLS = YES
    GEOPACKAGE_USE_SEARCH_ENVELOPE = NO
    INTERACT = NONE
    ORDER_RESULTS = No
    OUTPUT_ADD_SCHEMA_ATTRIBUTES = NO
    OUTPUT_FEATURES_DISPLAY = Schema and Data Features
    NoiseControlAreas -> PointOnAreaOverlayer [AREA]

Bookmark: Clean up attributes
Note: Assign a score based on noise control area
AttributeValueMapper_2
    DEFAULT_VALUE = 0
    LUT = Schedule C,200,Schedule F,50,Intermediate,100
    MAPPING_DIRECTION = FORWARD
    SRC = AreaName
    VAL_ATTR = NoiseZoneScore
