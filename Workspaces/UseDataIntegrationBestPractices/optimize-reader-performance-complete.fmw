FME workspace optimize-reader-performance-complete.fmw

Parameters:
- FEATURE_TYPES =
- SourceDataset_OGCKML = https://s3.amazonaws.com/FMEData/FMEData/Data/Boundaries/VancouverNeighborhoods.kml   # Source Google KML File or URL
- SourceDataset_MITAB = https://s3.amazonaws.com/FMEData/FMEData/Data/Parks.zip   # Source MapInfo TAB File(s)
- DestDataset_GEOTIFF = C:\FMEData\Output\Training   # Destination GeoTIFF Folder
- DestDataset_XLSXW = C:\FMEData\Output\Training\Neighborhoods.xlsx   # Destination Microsoft Excel File

Readers:
- XLSXR_1: XLSXR from https://s3.amazonaws.com/FMEData/FMEData/Data/Culture/PublicArt.xlsx in LL84
- MITAB_1: MITAB from $(SourceDataset_MITAB)
- OGCKML_1: OGCKML from $(SourceDataset_OGCKML)

Writers:
- XLSXW_2: XLSXW to $(DestDataset_XLSXW)
- GEOTIFF_1: GEOTIFF to $(DestDataset_GEOTIFF)

Note: 100m buffer around parks
Bufferer
    ANGLE = 22.5
    CAP_STYLE_LOOKUP = CAP_ARC
    CORNER_STYLE_LOOKUP = JOIN_ARC
    MODE = AREA
    OFFSET = 100
    OFFSET_UNITS = NONE
    PRECISION = APPROX
    SHOW_ERROR_INDICATORS = No
    CAP_STYLE = Arc
    CORNER_STYLE = Arc
    BUFFERED -> PointOnAreaOverlayer [AREA]
Reprojector_2
    DEST = UTM83-10
    INTERPOLATION_TYPE = ,NearestNeighbor
    RASTER_CELL_SIZE_LOOKUP = ,PreserveCells
    RASTER_TOLERANCE = 0.0
    SHOW_ERROR_INDICATORS = No
    INTERPOLATION_TYPE_NAME = Nearest Neighbor
    RASTER_CELL_SIZE = Preserve Cells
    REPROJECTED -> Clipper [CLIPPER]
    REPROJECTED -> Dissolver

Bookmark: Parks
Parks (reader MITAB_1)
    attributes: ParkId smallint, RefParkId smallint, ParkName char(40), NeighborhoodName char(40), VisitorCount smallint, TreeCount smallint, DogPark char(1), Washrooms char(1), SpecialFeatures char(1)
    -> Bufferer

Bookmark: Public Art
Downtown (reader XLSXR_1)
    attributes: Name char(51), Title char(51), Longitude x_coordinate, Latitude y_coordinate
    -> Reprojector

Bookmark: Reproject
Reprojector
    DEST = UTM83-10
    INTERPOLATION_TYPE = ,NearestNeighbor
    RASTER_CELL_SIZE_LOOKUP = ,PreserveCells
    RASTER_TOLERANCE = 0.0
    SHOW_ERROR_INDICATORS = No
    INTERPOLATION_TYPE_NAME = Nearest Neighbor
    RASTER_CELL_SIZE = Preserve Cells
    REPROJECTED -> 2DEllipseReplacer
    REPROJECTED -> PointOnAreaOverlayer [POINT]

Bookmark: Overlay points on parks
PointOnAreaOverlayer
    ATTR_ACCUM_MODE = Merge Incoming
    ATTR_CONFLICT_RES_LOOKUP = ORIGINAL_IF_CONFLICT
    DEAGGREGATE_INPUT = Yes
    OV_ATTR = _overlaps
    POLYS_FIRST = NO
    SHOW_ERROR_INDICATORS = No
    ATTR_CONFLICT_RES = Use Original
    AREA -> Tester
Tester
    BOOL_OP = OR
    SHOW_ERROR_INDICATORS = No
    TEST_CLAUSE = TEST @Value(_overlaps) = 0
    TEST_MODE = TEST
    PASSED -> VectorOnRasterOverlayer [VECTOR]
    PASSED -> Sorter
    FAILED -> VectorOnRasterOverlayer [VECTOR]

Bookmark: Prepare Data for Excel Writer
Sorter
    SHOW_ERROR_INDICATORS = No
    SORT_PARM = _overlaps NUMERIC ASCENDING ParkName ALPHA ASCENDING
    SORTED -> DuplicateFilter
DuplicateFilter
    INPUT_ORDERED_CHOICE_LOOKUP = NO
    KEYATTR = ParkName
    PRESERVE_FEATURE_ORDER_LOOKUP = PER_OUTPUT_PORT
    SHOW_ERROR_INDICATORS = No
    INPUT_ORDERED_CHOICE = No
    UNIQUE -> AttributeRemover
AttributeRemover
    REMOVE_ATTRS = Latitude,Longitude
    SHOW_ERROR_INDICATORS = No
    -> AttributeRenamer
AttributeRenamer
    ATTR_TABLE = RENAME_SET_DEFAULT _overlaps > ArtWorks
    KEEP_RENAMED_ONLY = no
    MISSING_INPUT_ATTRS = REMOVE
    SHOW_ERROR_INDICATORS = No
    -> Sheet1 (writer XLSXW_2)

Bookmark: Excel Writer
Sheet1 (writer XLSXW_2)
    attributes: ParkId number(20), ParkName string(40), NeighborhoodName string(40), VisitorCount number(20), ArtWorks number(20)

Bookmark: Create Ellipses
2DEllipseReplacer
    PRIMAXIS = 20
    ROT = 0
    SECAXIS = 20
    SHOW_ERROR_INDICATORS = No
    ELLIPSE -> FeatureColorSetter
FeatureColorSetter
    ALGORITHM = MANUAL
    COLOR = 0.666667,0,0
    FILL_COLOR = 1,0,0
    SHOW_ERROR_INDICATORS = No
    MODE = Fixed
    COLORED -> VectorOnRasterOverlayer [VECTOR]

Bookmark: Neighborhoods
Neighborhoods (reader OGCKML_1)
    attributes: NeighborhoodId kml_buffer, NeighborhoodName kml_buffer, NeighborhoodURL kml_buffer, TotalPopulation2001 kml_buffer, TotalPopulation2011 kml_buffer
    -> Reprojector_2

Bookmark: Orthophotos
Dissolver
    ACCUM_INPUT_ATTRS_LOOKUP = One
    CLEANING_TOLERANCE_LOOKUP = AUTO
    CONNECT_Z_MODE_LOOKUP = FIRST_WINS
    DEAGGREGATE_INPUT = Yes
    SHOW_ERROR_INDICATORS = No
    AREA -> FeatureReader [INITIATOR]
FeatureReader
    ATTRIBUTES = GEOTIFF,
    CLIP_TO_ENVELOPE = NO
    COMBINE_ATTRS_OPTIONS = RESULT_ONLY
    COMBINE_GEOM_OPTIONS = RESULT_ONLY
    DATASET = ""C:\FMEData\Data\Orthophotos\02-03-HI.tif" "C:\FMEData\Data\Orthophotos\02-03-JK.tif" "C:\FMEData\Data\Orthophotos\02-03-LM.tif" "C:\FMEData\Data\Orthophotos\02-03-NO.tif" "C:\FMEData\Data\Orthophotos\04-05-HI.tif" "C:\FMEData\Data\Orthophotos\04-05-JK.tif" "C:\FMEData\Data\Orthophotos\04-05-LM.tif" "C:\FMEData\Data\Orthophotos\04-05-NO.tif" "C:\FMEData\Data\Orthophotos\04-05-PQ.tif" "C:\FMEData\Data\Orthophotos\04-05-RS.tif" "C:\FMEData\Data\Orthophotos\06-07-HI.tif" "C:\FMEData\Data\Orthophotos\06-07-JK.tif" "C:\FMEData\Data\Orthophotos\06-07-LM.tif" "C:\FMEData\Data\Orthophotos\06-07-NO.tif" "C:\FMEData\Data\Orthophotos\06-07-PQ.tif" "C:\FMEData\Data\Orthophotos\06-07-RS.tif" "C:\FMEData\Data\Orthophotos\08-09-HI.tif" "C:\FMEData\Data\Orthophotos\08-09-JK.tif" "C:\FMEData\Data\Orthophotos\08-09-LM.tif" "C:\FMEData\Data\Orthophotos\08-09-NO.tif" "C:\FMEData\Data\Orthophotos\08-09-PQ.tif" "C:\FMEData\Data\Orthophotos\08-09-RS.tif" "C:\FMEData\Data\Orthophotos\10-11-HI.tif" "C:\FMEData\Data\Orthophotos\10-11-JK.tif" "C:\FMEData\Data\Orthophotos\10-11-LM.tif" "C:\FMEData\Data\Orthophotos\10-11-NO.tif" "C:\FMEData\Data\Orthophotos\10-11-PQ.tif" "C:\FMEData\Data\Orthophotos\10-11-RS.tif" "C:\FMEData\Data\Orthophotos\12-13-HI.tif" "C:\FMEData\Data\Orthophotos\12-13-JK.tif" "C:\FMEData\Data\Orthophotos\12-13-LM.tif" "C:\FMEData\Data\Orthophotos\12-13-NO.tif" "C:\FMEData\Data\Orthophotos\12-13-PQ.tif" "C:\FMEData\Data\Orthophotos\12-13-RS.tif" "C:\FMEData\Data\Orthophotos\14-15-HI.tif" "C:\FMEData\Data\Orthophotos\14-15-JK.tif" "C:\FMEData\Data\Orthophotos\14-15-LM.tif" "C:\FMEData\Data\Orthophotos\14-15-NO.tif" "C:\FMEData\Data\Orthophotos\14-15-PQ.tif" "C:\FMEData\Data\Orthophotos\14-15-RS.tif""
    FORMAT = GEOTIFF
    GEOMETRY_TYPES = GEOTIFF,""",fme_raster"""
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_SCALE_COLOR_TO_STANDARD_BIT_DEPTH = YES
    GEOTIFF_USE_APPROXIMATE_WORLDFILES = no
    GEOTIFF_USE_SEARCH_ENVELOPE = NO
    INITIATOR_FIRST_OUTPUT = default
    INPUT_PORT_INITIATOR_CONNECTED = CONNECTED
    INTERACT = INTERSECTS
    ORDER_RESULTS = No
    OUTPUT_ADD_SCHEMA_ATTRIBUTES = NO
    OUTPUT_FEATURES = BASED_ON_CONNECTIONS
    OUTPUT_USE_SCHEMA_CACHE = YES
    READER_BEHAVIOR = Constraint Parameters
    SHOW_ERROR_INDICATORS = No
    ATTR_ACCUM_MODE = Only Use Result
    COMBINE_GEOM = Use Result
    OUTPUT_FEATURES_DISPLAY = Schema and Data Features
    GEOTIFF -> RasterMosaicker

Bookmark: Combine orthophotos
RasterMosaicker
    ACCUM_ATTRS = ONE
    INTERPOLATION_TYPE = NearestNeighbor
    MERGE_PALETTES_NAME = Yes
    NODATA_OVERWRITE = No
    OVERLAPPING_VALUES = last
    SHOW_ERROR_INDICATORS = No
    SNAPPING_TYPE = RESAMPLE
    ACCUM_ATTRS_NAME = Use Attributes From One Feature
    INTERPOLATION_TYPE_NAME = Nearest Neighbor
    MERGE_PALETTES = Yes
    SNAPPING_TYPE_NAME = Resample
    -> VectorOnRasterOverlayer [RASTER]

Bookmark: Overlay parks on raster
VectorOnRasterOverlayer
    ALPHA = 1.0
    ANTI_ALIASING = No
    COMPOSITE_USING_ALPHA_BAND_LOOKUP = no
    SHOW_ERROR_INDICATORS = No
    TOLERANCE = 0.5
    COMPOSITE_USING_ALPHA_BAND = No
    RASTER -> Clipper [CANDIDATE]

Bookmark: Clip raster to neighborhoods
Clipper
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_PARTS
    MISSING_M_MODE_LOOKUP = LINEAR
    MISSING_Z_MODE_LOOKUP = LINEAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Linear Interpolation
    INSIDE -> RasterSelector

Bookmark: Raster processing
RasterSelector
    BAND_LIST = ALL ALL
    SELECTION_MODE_LOOKUP = USER
    SHOW_ERROR_INDICATORS = No
    SELECTION_MODE = Band and Palette List
    -> RasterBandNodataSetter
RasterBandNodataSetter
    NODATA_VALUE = 0
    REPLACE_CELL_VALUES_LOOKUP = DoNotReplaceCellValues
    SHOW_ERROR_INDICATORS = No
    REPLACE_CELL_VALUES = No
    -> Raster1 (writer GEOTIFF_1)

Bookmark: GeoTIFF Writer
Raster1 (writer GEOTIFF_1)
