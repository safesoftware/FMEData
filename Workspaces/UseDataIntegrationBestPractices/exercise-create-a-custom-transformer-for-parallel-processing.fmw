FME workspace exercise-create-a-custom-transformer-for-parallel-processing.fmw

Parameters:
- SourceDataset_FILEGDB = https://s3.amazonaws.com/FMEData/FMEData/Data/Addresses/Addresses.gdb.zip   # File Geodatabase
- SourceDataset_OSM = https://s3.amazonaws.com/FMEData/FMEData/Data/OpenStreetMap/building.osm   # Source OpenStreetMap File(s)
- SourceDataset_MITAB = https://s3.amazonaws.com/FMEData/FMEData/Data/Zoning.zip   # Source MapInfo TAB File(s)
- DestDataset_FFS = C:\FMEData\Output\Training\ValidatedBuildings.ffs   # Destination FME Feature Store (FFS) File

Readers:
- FILEGDB_1: FILEGDB from $(SourceDataset_FILEGDB)
- OSM_1: OSM from $(SourceDataset_OSM)
- MITAB_1: MITAB from $(SourceDataset_MITAB)

Writers:
- FFS_1: FFS to $(DestDataset_FFS)

PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> PointOnAreaOverlayer [POINT]
PostcodeBoundaries (reader FILEGDB_1)
    attributes: OBJECTID objectid, CFSAUID text(3), SHAPE_Length double, SHAPE_Area double
Junction
    -> ValidatedBuildings (writer FFS_1)
Note: Write Output
ValidatedBuildings (writer FFS_1)
    attributes: OBJECTID int32, GlobalID buffer, OWNERNM1 varchar(150), OWNERNM2 varchar(150), PSTLADDRESS varchar(250), PSTLCITY varchar(100), PSTLPROV varchar(25), INTSTATE varchar(5), INTPSTLCD varchar(10), COUNTRY varchar(100), REPRESENT varchar(14), STATUS varchar(9), LASTUPDATE datetime, LASTEDITOR varchar(50), POSTALCODE varchar(6), _ValidationZones varchar(100), _ValidationAddress varchar(100)

Bookmark: Read OpenStreetMap Buildings
building (reader OSM_1)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, military xml_buffer, denomination xml_buffer, ref:ruian:building xml_buffer, building:ruian:type xml_buffer, construction xml_buffer, fixme xml_buffer, tourism xml_buffer, ref:bag xml_buffer, source:date xml_buffer, religion xml_buffer, amenity xml_buffer, start_date xml_buffer, layer xml_buffer, building:use:pl xml_buffer, addr:housenumber xml_buffer, addr:city xml_buffer, addr:postcode xml_buffer, power xml_buffer, substation xml_buffer,
      building:usage:pl xml_buffer, building:levels xml_buffer, name xml_buffer, addr:street xml_buffer, height xml_buffer, building xml_buffer
    -> GeometryFilter
GeometryFilter
    FILTER_MODE = COMPLETE
    FILTER_MULTI = FILTER_TYPES]Polygon Donut MultiArea]FILTER_TYPES_Complete]Polygon Donut MultiArea]INSTANCES]INSTANCE
    FILTER_TYPES = Polygon Donut MultiArea
    FILTER_TYPES_Complete = Polygon Donut MultiArea
    INSTANCES = INSTANCE
    Polygon -> Reprojector
    Donut -> Reprojector
    MultiArea -> Reprojector
Reprojector
    DEST = UTM83-10
    INTERPOLATION_TYPE = NearestNeighbor
    RASTER_CELL_SIZE = PreserveCells
    RASTER_TOLERANCE = 0.0
    REPROJECTED -> PointOnAreaOverlayer [AREA]

Bookmark: Get and Test Address
Note: Get Address from Overlapping Address
PointOnAreaOverlayer
    ATTR_ACCUM_MODE = HANDLE_CONFLICT
    ATTR_CONFLICT_RES = ORIGINAL_IF_CONFLICT
    DEAGGREGATE_INPUT = Yes
    OV_ATTR = _overlaps
    POLYS_FIRST = NO
    AREA -> Tester
Tester
    BOOL_OP = OR
    TEST_CLAUSE = TEST @Value(_overlaps) > 0
    TEST_MODE = TEST
    PASSED -> GeometryValidator
    FAILED -> AttributeCreator
Note: Set Validation Error
AttributeCreator
    ATTR_TABLE = SET_TO _ValidationAddress (varchar(200)) = No matching address point
    -> GeometryValidator

Bookmark: Validate Geometry
GeometryValidator
    ISSUE_ATTR_NAME = _issues
    PRESETS = All
    REPAIR = YES
    RULES = AREA_ORIENTATION AREA_ORIENTATION]VALID]FME_CONTROLLER_QUERY_FILE]transformers\dependencies\geometryvalidator\AREA_ORIENTATION.fme]FME_CONTROLLER_CHOICE]AREA_ORIENTATION CONSECUTIVE_IDENTICAL_VERTICES_2D CHECK_Z]YES]TOLERANCE]0.0]FME_CONTROLLER_QUERY_FILE]transformers\dependencies\geometryvalidator\CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers\dependencies\geometryvalidator\NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.1.0]SPATIAL_SUBSET]<Unused>]REQUIRE_SIMPLE]Yes]LEGACY_OGC]No]FME_CONTROLLER_QUERY_FILE]]FME_CONTROLLER_CHOICE]OGC_VALID_CHECK OGC_VALID_CHECK OGC_VERSION]V1.2.0]SPATIAL_SUBSET]<Unused>]REQUIRE_SIMPLE]No]LEGACY_OGC]No]FME_CONTROLLER_QUERY_FILE]transformers\dependencies\geometryvalidator\OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers\dependencies\geometryvalidator\PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]VALIDATE_CURVES_POINTS]Yes]INTERSECT_ACROSS_MULTIS]No]FME_CONTROLLER_QUERY_FILE]transformers\dependencies\geometryvalidator\SELF_INTERSECTING.fme]FME_CONTROLLER_CHOICE]SELF_INTERSECTING SHELL_VALIDATION FLIP_APPEARANCE_MODE]FLIP_APPEARANCES]FME_CONTROLLER_QUERY_FILE]transformers\dependencies\geometryvalidator\SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers\dependencies\geometryvalidator\TYPE_REPAIR.fme]FME_CONTROLLER_CHOICE]TYPE_REPAIR MISMATCHED_DIMENSIONS FORCE_DIMENSION]2D]MISMATCHED_Z_VAL]<Unused>]FME_CONTROLLER_QUERY_FILE]transformers\dependencies\geometryvalidator\MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers\dependencies\geometryvalidator\MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = DETAILED_SUMMARY
    PASSED -> SpatialRelator [Requestor]
    FAILED -> SpatialRelator [Requestor]
    REPAIRED -> SpatialRelator [Requestor]
    ISSUE_LOCATIONS -> SpatialRelator [Requestor]
    INVALID_PARTS -> SpatialRelator [Requestor]

Bookmark: Get and Test Zoning
Zones (reader MITAB_1)
    attributes: ZoneName char(30), ZoneCategory char(30)
    -> SpatialRelator [Supplier]
SpatialRelator
    AGGREGATE_HANDLING = Yes
    CALC_CARD = No
    CURVE_BOUNDARY_RULE_PARAM = Default Rule
    PREDICATES = INTERSECTS
    SUCCESS_ATTR = _related_candidates
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(_related_candidates) = 0",Unzoned,"BOOL_OP,OR,COMPOSITE_TEST,""""""1"""""",TEST_CLAUSE,TEST @Value(_related_candidates) > 1",Multi-Zoned
    Unzoned -> AttributeCreator_2
    Multi-Zoned -> AttributeCreator_3
    <UNFILTERED> -> Junction
AttributeCreator_2
    ATTR_TABLE = SET_TO _ValidationZones (varchar(200)) = Unzoned building
    -> Junction
AttributeCreator_3
    ATTR_TABLE = SET_TO _ValidationZones (varchar(200)) = Overlapping zones building
    -> Junction
