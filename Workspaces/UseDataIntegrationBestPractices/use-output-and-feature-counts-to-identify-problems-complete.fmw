FME workspace use-output-and-feature-counts-to-identify-problems-complete.fmw

Parameters:
- SourceDataset_OGCKML = https://s3.amazonaws.com/FMEData/FMEData/Data/Boundaries/VancouverNeighborhoods.kml   # Source Google KML File or URL
- SourceDataset_CSV2 = https://s3.amazonaws.com/FMEData/FMEData/Resources/FormBasic/street-trees.csv   # Source CSV (Comma Separated Value) File(s)

Readers:
- OGCKML_1: OGCKML from $(SourceDataset_OGCKML)
- CSV2_1: CSV2 from $(SourceDataset_CSV2)

Note: This should clip trees to the combined boundary of all Neighborhoods
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation

Bookmark: Source Data
Neighborhoods (reader OGCKML_1)
    attributes: NeighborhoodId kml_buffer, NeighborhoodName kml_buffer, NeighborhoodURL kml_buffer, TotalPopulation2001 kml_buffer, TotalPopulation2011 kml_buffer
    -> Reprojector_2
Reprojector_2
    DEST = UTM83-10
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CLIPPER]

Bookmark: Street Trees
CSV (reader CSV2_1)
    attributes: TREE_ID uint32, CIVIC_NUMBER uint32, STD_STREET varchar(20), GENUS_NAME varchar(19), SPECIES_NAME varchar(18), CULTIVAR_NAME varchar(20), COMMON_NAME varchar(30), ASSIGNED varchar(1), ROOT_BARRIER varchar(1), PLANT_AREA varchar(2), ON_STREET_BLOCK uint32, ON_STREET varchar(20), NEIGHBOURHOOD_NAME varchar(24), STREET_SIDE_NAME varchar(8), HEIGHT_RANGE_ID uint32, DIAMETER real32, CURB varchar(1), DATE_PLANTED date, Geom varchar(58)
    -> Tester
Tester
    BOOL_OP = OR
    TEST_CLAUSE = TEST Geom ATTRIBUTE_HAS_A_VALUE ""
    TEST_MODE = TEST
    PASSED -> JSONExtractor
JSONExtractor
    EXTRACT_QUERY_TABLE = lat json["coordinates"][1] long json["coordinates"][0]
    JSON_DOCUMENT = @Value(Geom)
    READ_FROM_FILE = NO
    EVALUATED -> VertexCreator
VertexCreator
    COORDSYS = LL84
    MEASURE_TYPE_LOOKUP = CONTINUOUS
    MODE = REPLACE
    REMOVE_ATTRIBUTES = No
    XVAL = @Value(long)
    YVAL = @Value(lat)
    MEASURE_TYPE = Continuous
    MODE_NAME = Replace with Point
    -> Reprojector
Reprojector
    DEST = UTM83-10
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CANDIDATE]
