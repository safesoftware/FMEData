FME workspace manage-connections-complete.fmw

Parameters:
- AddressID = 127209   # Enter Address ID
- SourceDataset_FILEGDB = https://s3.amazonaws.com/FMEData/FMEData/Data/CommunityMapping/CommunityMap.gdb.zip   # File Geodatabase
- SourceDataset_POSTGIS = FME Training PostGIS Database   # Connection

Readers:
- OPENFILEGDB_1: OPENFILEGDB from $(SourceDataset_FILEGDB)
- POSTGIS_1: POSTGIS from $(SourceDataset_POSTGIS)

Note: You will need to provide your own Google Drive web connection for these to work..

Bookmark: PostGIS
DatabaseQuerier
    DATASET = FME Training PostGIS Database
    EXPOSED_ATTRIBUTE_LIST = AddressId,PostalAddressId,SiteAddressKey,OwnerName1,OwnerName2,PostalAddress,PostalCity,PostalProvince,PostalCode,Country,PostBoxType,PostBoxId,PostBoxGroup,Represent,Status,LastUpdate,LastEditor
    FORMAT = POSTGIS
    GEOMETRY_TYPES = "geom,fme_collection,fme_no_geom,fme_area,fme_line,fme_point,fme_surface"
    INPUT_PORT_INITIATOR_CONNECTED = *
    OUTPUT_FEATURES = DATA_ONLY
    POSTGIS_CREATE_FEATURE_TABLES_FROM_DATA = Yes
    POSTGIS_DISABLE_COLLECTION_SPLITTING = yes
    POSTGIS_NAMED_CONNECTION = FME Training PostGIS Database
    POSTGIS_QUERY_FEATURE_TYPES_FOR_MERGE_FILTERS = Yes
    POSTGIS_READ_TIME_WITH_TIMEZONE = Yes
    POSTGIS_USE_TRUE_POSTGIS_TYPES = yes
    SQL_STATEMENT:
      SELECT * FROM "public"."PostalAddress"
      WHERE "AddressId" = $(AddressID)
    RESULT -> PointOnAreaOverlayer [POINT]
PostalAddress (reader POSTGIS_1) [off]
    attributes: AddressId int4, PostalAddressId varchar(40), SiteAddressKey varchar(20), OwnerName1 varchar(50), OwnerName2 varchar(50), PostalAddress varchar(50), PostalCity varchar(30), PostalProvince varchar(5), PostalCode varchar(7), Country varchar(40), PostBoxType varchar(10), PostBoxId varchar(25), PostBoxGroup varchar(50), Represent varchar(15), Status varchar(13), LastUpdate date, LastEditor varchar(30)
    -> PointOnAreaOverlayer [POINT]

Bookmark: Geodatabase
GarbageSchedule (reader OPENFILEGDB_1)
    attributes: Zone text(30), Subzone text(30), Schedule text(30), NumAddresses smallint, OBJECTID largeint
    -> PointOnAreaOverlayer [AREA]

Bookmark: Overlay address on garbage zone then generate report
PointOnAreaOverlayer
    ATTR_ACCUM_MODE = HANDLE_CONFLICT
    ATTR_CONFLICT_RES = ORIGINAL_IF_CONFLICT
    DEAGGREGATE_INPUT = Yes
    OV_ATTR = _overlaps
    POLYS_FIRST = NO
    POINT -> HTMLReportGenerator
HTMLReportGenerator
    CONTENT_LIST = HEADER HTML HTML HTML HTML
    PAGE_CONFIG = HEADER{{TEXT;Garbage Collection Day;HEADER;H2;HEADER_ID;;ALIGNMENT;LEFT;COLOR_Header;0,0,0;COLOR;0,0,0}}HTML{{HTML;<h3><strong>Property: </strong>@Value(AddressId)</h3>}}HTML{{HTML;<h3><strong>Address: </strong>@Value(PostalAddress), @Value(PostalCity)</h3>}}HTML{{HTML;<h3><strong>Garbage Zone: </strong>@Value(Zone), @Value(Subzone)</h3>}}HTML{{HTML;<h3><strong>Collection Day: </strong>@Value(Schedule)</h3>}}
    TITLE = Garbage Collection Day
    -> FeatureWriter [HTML]

Bookmark: Write out to HTML
FeatureWriter
    CONFIG_PARAMETERS = ESCAPE_COMMAS_IN_FTP_FORMAT_PARAMETERS,no
    DATASET = C:\FMEData\Output\Training\GarbageSchedule.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
    SUMMARY -> GoogleDriveConnector
    SUMMARY -> GoogleDriveConnector_2

Bookmark: GoogleDrive
Note: Upload
GoogleDriveConnector
    GOOGLEDRIVE_NAMED_CONNECTION = sam.walker_safe Google Drive
    INPUT_PORT_CONNECTED = CONNECTED
    OPERATION_TYPE = Upload
    PARAMETER_SETUP = _FME_SOURCE_TYPE_Upload;File;_FME_SOURCE_FILE;@Value(_dataset);_FME_SOURCE_FOLDER;<Unused>;_FME_INCLUDE_SUBFOLDERS_Upload;<Unused>;_FME_CONTENTS_ONLY;<Unused>;_FME_DATA_TO_UPLOAD;<Unused>;_FME_UPLOAD_DESTINATION_PATH;[{"display":"Personal/","value":"1OizauqFU9i5IfaZs8WmH2k8tYGLVfhm1"}];_FME_UPLOAD_ATTR_FILENAME;<Unused>;_UPLOAD_FME_ATTRIBUTES_TO_ADD;_sharable_link _direct_download_link _id;_FME_SOURCE_TYPE;File
    _FME_SOURCE_FILE = @Value(_dataset)
    _FME_SOURCE_TYPE = File
    _FME_SOURCE_TYPE_Upload = File
    _FME_UPLOAD_DESTINATION_PATH = [{"display":"Personal/","value":"1OizauqFU9i5IfaZs8WmH2k8tYGLVfhm1"}]
    _UPLOAD_FME_ATTRIBUTES_TO_ADD = _sharable_link _direct_download_link _id
Note: List
GoogleDriveConnector_2
    GOOGLEDRIVE_NAMED_CONNECTION = sam.walker_safe Google Drive
    INPUT_PORT_CONNECTED = CONNECTED
    OPERATION_TYPE = List
    PARAMETER_SETUP = _FME_FILES_List;[{"display":"/","value":"/"}];_FME_INCLUDE_SUBFOLDERS_List;No;_LIST_FME_ATTRIBUTES_TO_ADD;_name _sharable_link _id _file_or_folder _file_size _file_last_modified _relative_path;_FME_FILES;[{"display":"/","value":"/"}];_FME_INCLUDE_SUBFOLDERS;No
    _FME_FILES = [{"display":"/","value":"/"}]
    _FME_FILES_List = [{"display":"/","value":"/"}]
    _FME_INCLUDE_SUBFOLDERS = No
    _FME_INCLUDE_SUBFOLDERS_List = No
    _LIST_FME_ATTRIBUTES_TO_ADD = _name _sharable_link _id _file_or_folder _file_size _file_last_modified _relative_path
