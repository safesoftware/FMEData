FME workspace exercise-workspace-prototyping-complete.fmw
Title: MULTI to MULTI

Readers:
- SHAPEFILE_1: SHAPEFILE from c:\FMEData\Resources\FMEAccelerator\data\road-ahead-upcoming-projects.zip
- CSV2_1: CSV2 from c:\FMEData\Resources\FMEAccelerator\data\business-licences.zip
- CSV2_2: CSV2 from c:\FMEData\Resources\FMEAccelerator\data\food-vendors.csv in LL84
- SQLITE3_2: SQLITE3 from C:\FMEData\Data\Planning\business-licences-sqlite.zip

Writers:
- XLSXW_1: XLSXW to c:\FMEData\Output\Training\AffectedVendors.xlsx in LL84

Bookmark: Source Data
Note: Upcoming road construction projects (SHP)
road-ahead-upcoming-projects (reader SHAPEFILE_1)
    attributes: project char(255), street char(255), location char(255), comp_date date, url_link char(255)
    -> Bufferer
Note: Food Vendors CSV
CSV (reader CSV2_2)
    attributes: KEY varchar(5), VENDOR_TYPE varchar(12), STATUS varchar(5), BUSINESS_NAME varchar(29), LOCATION varchar(76), DESCRIPTION varchar(35), GEO_LOCALAREA varchar(25), x x_coordinate, y y_coordinate
    -> AttributeValidator
Note: Business Licenses SQLite
business-licences (reader SQLITE3_2)
    attributes: FOLDERYEAR integer, LicenceRSN integer, LicenceNumber varchar(10), LicenceRevisionNumber integer, BusinessName varchar(89), BusinessTradeName varchar(77), Status varchar(21), IssuedDate varchar(26), ExpiredDate varchar(11), BusinessType varchar(41), BusinessSubType varchar(35), Unit varchar(11), UnitType varchar(6), House varchar(9), Street varchar(21), City varchar(10), Province varchar(3), Country varchar(3), PostalCode varchar(11), LocalArea varchar(25), NumberofEmployees float, FeePaid integer, ExtractDate varchar(26), Geom varchar(72)
    -> Tester

Bookmark: Determine Impacted Area
Bufferer
    ANGLE = 22.5
    CAP_STYLE = Arc
    CORNER_STYLE = Arc
    MODE = AREA
    OFFSET = 50
    OFFSET_UNITS = FEET
    PRECISION = APPROX
    BUFFERED -> SpatialFilter [Filter]

Bookmark: Validate Food Truck Data
AttributeValidator
    TABLE = KEY$ATTRIBUTE_UNIQUE$<Unused>/BUSINESS_NAME$ATTRIBUTE_HAS_A_VALUE$<Unused>
    PASSED -> SpatialFilter [Candidate]

Bookmark: Find Impacts
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureJoiner [LEFT]

Bookmark: Get Current License Data
Note: Faster to use a WHERE clause on the reader feature type
Tester
    BOOL_OP = AND
    TEST_CLAUSE:
      TEST @Value(FOLDERYEAR) = 21
      TEST @Value(Status) != Gone Out of Business
    TEST_MODE = TEST
    PASSED -> FeatureJoiner [RIGHT]

Bookmark: Join Data and Manage Attributes
FeatureJoiner
    ATTR_CONFLICT_RES = Prefer Left
    GEOMETRY_HANDLING = Prefer Left
    JOIN_KEYS = BUSINESS_NAME BusinessTradeName AUTO
    JOIN_MODE = Inner
    JOINED -> AttributeManager
AttributeManager
    ATTR_TABLE:
      RENAME_SET_VALUE BUSINESS_NAME > Business Name (varchar(29))
      REMOVE VENDOR_TYPE (varchar(12))
      RENAME_SET_VALUE DESCRIPTION > Description (varchar(35))
      RENAME_SET_VALUE LOCATION > Location (varchar(76))
      RENAME_SET_VALUE STATUS > Status (varchar(5))
      RENAME_SET_VALUE project > Street Project (char(255))
      RENAME_SET_VALUE street > Street (char(255))
      RENAME_SET_VALUE location > Location (char(255))
      RENAME_SET_VALUE comp_date > Completion Date (date)
      RENAME_SET_VALUE url_link > Project Information Link (char(255))
      REMOVE KEY (varchar(5))
      REMOVE GEO_LOCALAREA (varchar(25))
      REMOVE _predicate (buffer)
      REMOVE FOLDERYEAR (uint32)
      REMOVE LicenceRSN (uint32)
      RENAME_SET_VALUE LicenceNumber > Business License Number (varchar(10))
      REMOVE LicenceRevisionNumber (uint32)
      REMOVE BusinessName (varchar(89))
      REMOVE BusinessTradeName (varchar(77))
      REMOVE Status (varchar(21))
      REMOVE IssuedDate (varchar(26))
      REMOVE ExpiredDate (varchar(11))
      REMOVE BusinessType (varchar(41))
      REMOVE BusinessSubType (varchar(35))
      REMOVE Unit (varchar(11))
      REMOVE UnitType (varchar(6))
      REMOVE House (varchar(9))
      REMOVE Street (varchar(21))
      REMOVE City (varchar(10))
      REMOVE Province (varchar(3))
      REMOVE Country (varchar(3))
      REMOVE PostalCode (varchar(11))
      REMOVE LocalArea (varchar(25))
      REMOVE NumberofEmployees (real32)
      REMOVE FeePaid (uint32)
      REMOVE ExtractDate (varchar(26))
      REMOVE Geom (varchar(72))
      REMOVE x (real64)
      REMOVE y (real64)
    -> AffectedVendors (writer XLSXW_1)

Bookmark: Create a Report in Excel
AffectedVendors (writer XLSXW_1)
    attributes: Business Name string(29), Description string(35), Street Project string(255), Location string(255), Completion Date date(20), Project Information Link string(255), Business License Number string(10)
