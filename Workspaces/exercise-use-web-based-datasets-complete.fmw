FME workspace exercise-use-web-based-datasets-complete.fmw

Parameters:
- SourceDataset_ACAD = https://s3.amazonaws.com/FMEData/FMEData/Data/Transportation/CompleteRoads.dwg   # Source Autodesk AutoCAD DWG/DXF File(s)
- FEATURE_TYPES =

Readers:
- ACAD_1: ACAD from $(SourceDataset_ACAD) in UTM84-10N

Arterial (reader ACAD_1)
    attributes: From_HBlock char(9), HBlock char(26), OneWay char(1), StreetId number(5,0), StreetName char(18)
    -> DatabaseJoiner
DatabaseJoiner
    ADDED_FIELDS = EstimatedSnowfall LastTreated Temperature WeatherStation
    ATTR_ACCUM_MODE = Merge Joined
    ATTR_CONFLICT_RES = Use Original
    DATASET = https://s3.amazonaws.com/FMEData/Interopolis/Snowfall.xlsx
    FORMAT = XLSXR
    JOIN_KEYS = StreetId StreetId
    MATCH_RULE_DISPLAY = Match First (1:0..1+)
    TABLE = Snowfall
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_EXPOSED_ATTRS = xlsx_row_id,number(11,0)
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    JOINED -> KMLStyler
KMLStyler
    COLOR = FME_CONDITIONAL:DEFAULT_VALUE'1,0,0'BOOL_OP;OR;COMPOSITE_TEST;1;TEST @Value(EstimatedSnowfall) = 0'0,1,0.0666667'BOOL_OP;AND;COMPOSITE_TEST;1 AND 2;TEST @Value(EstimatedSnowfall) > 0;TEST @Value(EstimatedSnowfall) < 150'0.94902,1,0'FME_NUM_CONDITIONS3___
    FILL_OPACITY = 0.4
    ICON_OPACITY = 1.0
    ICON_SCALE = 0.8
    LABEL_OPACITY = 1.0
    LABEL_SCALE = 1.0
    LABEL_VISIBILITY_LOOKUP = 1
    LINE_WIDTH = 1.0
    LINE_WIDTH_UNITS_LOOKUP = PIXELS
    OPACITY = 1.0
    STYLE_PER_FEATURE = Yes
    LABEL_VISIBILITY = Yes
    LINE_WIDTH_UNITS = Pixels (Display Units)
    KMLStyled -> FeatureWriter [NewFeatureType]
FeatureWriter
    DATASET = C:\FMEData\Output\Training\RoadSnowfall.zip\RoadSnowfall.kml
    DATASET_ATTR = _dataset
    FEATURE_TYPE_LIST_ATTR = _feature_types
    FORMAT = OGCKML
    OGCKML_ATTR_IN_DESCRIPTION = yes
    OGCKML_AUTO_CREATE_NETWORK_LINKS = no
    OGCKML_COORDINATE_SYSTEM_GRANULARITY = FEATURE
    OGCKML_COPY_ICON = yes
    OGCKML_CREATE_EMPTY_FOLDERS = no
    OGCKML_DESTINATION_DATASETTYPE_VALIDATION = Yes
    OGCKML_DETECT_RASTERS = yes
    OGCKML_DOCUMENT_VISIBILITY = yes
    OGCKML_EXEC_GO_PIPELINE = no
    OGCKML_EXEC_PO_PIPELINE = no
    OGCKML_HTML_DESCRIPTIONS = yes
    OGCKML_KML21_FANOUT_TYPE = folder
    OGCKML_LOG_VERBOSE = no
    OGCKML_MOVE_TO_KML_LOCAL_COORDSYS = yes
    OGCKML_OMIT_DOCUMENT_ELEMENT = no
    OGCKML_ORIENTATION = none
    OGCKML_OUTPUT_SCHEMA = yes
    OGCKML_RASTER_FORMAT = tiff
    OGCKML_RASTER_MODE = write
    OGCKML_REGIONATE_DATA = no
    OGCKML_TEXTURE_FORMAT = NONE
    OGCKML_WRITE_3D_GEOM_AS_POLYGONS = no
    OGCKML_WRITE_TEXTURES_TXT_FILE = no
    TOTAL_FEATURES_WRITTEN_ATTR = _total_features_written
    SUMMARY -> FTPCaller
FTPCaller
    AUTH_TYPE = NONE
    CONNECTION_MODE = PASSIVE
    ERROR_ATTR = _error
    MODE_LOOKUP = BINARY
    PROXY_TYPE = FME
    REMOTE_URL = ftp://ftp.safe.com/incoming/training/@UUID()/@ReplaceString(@ReplaceString(@ReplaceRegularExpression(@Value(_dataset),\.zip(.*),,caseSensitive=TRUE),C:,,caseSensitive=TRUE),\,/,caseSensitive=TRUE).zip
    TRANSFER_TYPE_LOOKUP = UploadFromFile
    UPLOAD_FILE = @ReplaceRegularExpression(@Value(_dataset),\.zip(.*),,caseSensitive=TRUE).zip
    VERIFY_SSL_CERTIFICATES_LOOKUP = YES
    MODE = Binary
    TRANSFER_TYPE = Upload from a File
    VERIFY_SSL_CERTIFICATES = Yes
Creator
    GEOMTYPE = Geometry Object
    NUM = 1
Creator_2
    GEOMTYPE = Geometry Object
    NUM = 1
