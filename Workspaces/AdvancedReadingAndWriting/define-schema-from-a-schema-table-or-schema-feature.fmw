FME workspace define-schema-from-a-schema-table-or-schema-feature.fmw

Parameters:
- SourceDataset_GML = https://s3.amazonaws.com/FMEData/FMEData/Data/Emergency/FireHalls.gml   # Source Geography Markup Language (GML) File(s)
- FEATURE_TYPES =
- DestDataset_GML = C:\FMEData\Output\Training\NewCommunityMap.gml   # Destination Geography Markup Language (GML) File
- SourceDataset_MITAB = https://s3.amazonaws.com/FMEData/FMEData/Data/Parks.zip   # Source MapInfo TAB File(s)
- FEATURE_TYPES_2 =
- SourceDataset_OPENFILEGDB = https://s3.amazonaws.com/FMEData/FMEData/Data/CommunityMapping/CommunityMap.gdb.zip   # File Geodatabase

Readers:
- GML_3: GML from $(SourceDataset_GML)
- MITAB_2: MITAB from $(SourceDataset_MITAB)
- OPENFILEGDB_1: OPENFILEGDB from $(SourceDataset_OPENFILEGDB)

Writers:
- GML_1: GML to $(DestDataset_GML)

Bookmark: Reader Feature Types
Note: : FireHalls [GML]
FireHalls (reader GML_3)
    attributes: HallNumber xml_char(30), Name xml_char(30), Address xml_char(30), PhoneNumber xml_char(30), Engine xml_char(1), Ladder xml_char(1), Quint xml_char(1), Rescue xml_char(1), Medic xml_char(1), gml_pointProperty xml_geometry, gml_multiPointProperty xml_geometry
    -> DYNAMIC (writer GML_1)
Note: : Parks [MITAB]
Parks (reader MITAB_2)
    attributes: ParkId smallint, RefParkId smallint, ParkName char(40), NeighborhoodName char(40), VisitorCount smallint, TreeCount smallint, DogPark char(1), Washrooms char(1), SpecialFeatures char(1)
    -> DYNAMIC (writer GML_1)

Bookmark: Writer Feature Types
DYNAMIC (writer GML_1)
    attributes: LastUpdatedBy xml_char(30)
