FME workspace exercise-build-dynamic-workflows-with-a-multi-dataset-schemascanner-complete.fmw

Parameters:
- SourceDataset_CSV2 = https://s3.amazonaws.com/FMEData/FMEData/Resources/DynamicWorkflows/Data/Cedar%20Cottage.csv   # Source CSV (Comma Separated Value) File(s)
- FEATURE_TYPES =   # Feature Types to Read
- DestDataset_CSV2 = C:\FMEData\Output\Training   # Destination CSV (Comma Separated Value) Folder
- SourceDataset_CSV2_2 = https://s3.amazonaws.com/FMEData/FMEData/Resources/DynamicWorkflows/Data/Vancouver%20Farmers%20Markets.csv   # Source CSV (Comma Separated Value) File(s)
- FEATURE_TYPES_2 =   # Feature Types to Read

Readers:
- CSV2_1: CSV2 from $(SourceDataset_CSV2)
- CSV2_3: CSV2 from $(SourceDataset_CSV2_2)

Writers:
- CSV2_2: CSV2 to $(DestDataset_CSV2)

AttributeManager
    ATTR_TABLE:
      SET_TO Hours (varchar(200)) = @Value(Open)-@Value(Close)
      REMOVE Open (varchar(7))
      REMOVE Close (varchar(7))
    -> SchemaScanner
SchemaScanner
    CASE = No
    EMPTY_ATTR_HANDLING = INFER_EMPTY_SCHEMA
    GROUP_BY = Day
    HOLD = Yes
    IGNORE_REGEXP = fme_<pipe>csv_<pipe>multi_
    INCLUDE_FORMAT_ATTR = Yes
    NUMERIC_ALLOW_LEADING_ZEROES = Yes
    SCHEMA_NAME_ATTR = fme_feature_type_name
    UNBOUNDED_NUMBERS = Yes
    UNBOUNDED_STRINGS = No
    -> DYNAMIC (writer CSV2_2)
    <SCHEMA> -> DYNAMIC (writer CSV2_2)

Bookmark: Reader Feature Types
Note: Cedar Cottage CSV
CSV (reader CSV2_1)
    attributes: MarketType varchar(21), MarketName varchar(48), MergedAddress varchar(33), Day varchar(9), Open varchar(7), Close varchar(7), Months varchar(12), NumberOfVendors varchar(10)
    -> AttributeManager
Note: Vancouver Farmers Markets CSV
CSV (reader CSV2_3)
    attributes: MarketType varchar(1), MarketName varchar(33), MergedAddress varchar(34), Day varchar(9), Open varchar(4), Close varchar(4), Months varchar(23), NumberOfVendors uint32, Offerings varchar(51)
    -> AttributeManager

Bookmark: Writer Feature Types
DYNAMIC (writer CSV2_2)
