FME workspace exercise-map-schema-dynamically-with-the-schemamapper-complete.fmw

Parameters:
- SourceDataset_GML = https://s3.amazonaws.com/FMEData/FMEData/Data/Emergency/FireHalls.gml   # Source Geography Markup Language (GML) File(s)
- FEATURE_TYPES =
- DestDataset_GML = c:\FMEData\Output\Training\NewCommunityMap.gml   # Destination Geography Markup Language (GML) File
- SourceDataset_MITAB = https://s3.amazonaws.com/FMEData/FMEData/Data/Parks.zip   # Source MapInfo TAB File(s)
- FEATURE_TYPES_2 =
- SourceDataset_SCHEMA_FROM_TABLE = c:\FMEData\Resources\DesktopAdvanced\CommunityMapAdvancedSchema.xlsx   # Source Dataset
- SourceDataset_MITAB_3 = https://s3.amazonaws.com/FMEData/FMEData/Data/Zoning.zip   # Source MapInfo TAB File(s)
- DestDataset_GML_6 = c:\FMEData\Output\Training\NewCommunityMapSchemaFeature.gml   # Destination Geography Markup Language (GML) File

Readers:
- GML_1: GML from $(SourceDataset_GML)
- MITAB_1: MITAB from $(SourceDataset_MITAB)
- SCHEMA_FROM_TABLE_1: SCHEMA_FROM_TABLE from $(SourceDataset_SCHEMA_FROM_TABLE)
- MITAB_2: MITAB from $(SourceDataset_MITAB_3)

Writers:
- GML_2: GML to $(DestDataset_GML)
- GML_3: GML to $(DestDataset_GML_6)

SchemaMapper
    DATASET = c:\FMEData\Resources\DesktopAdvanced\CommunityMapAdvancedSchema.xlsx
    FORMAT = XLSXR
    IDXDESTATTR = fme_feature_type
    IDXDESTCOL = ""
    IDXSOURCEATTR = fme_feature_type
    IDXSOURCECOL = ""
    MAP_ATTRS = OldAttrName NewAttrName $(FME_ASC_16)
    ROW_ID_ATTR = _schemamapper_row_ids
    TABLE = Sheet2
    XLSXR_ALLOW_DOLLAR_SIGNS = YES
    XLSXR_APPLY_FILTERS = No
    XLSXR_CASE_SENSITIVE_FEATURE_TYPES = YES
    XLSXR_CONFIGURATION_DATASET = c:\FMEData\Resources\DesktopAdvanced\CommunityMapAdvancedSchema.xlsx
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA = Sheet2,0,OldAttrName,char,12,,,1,NewAttrName,char,12,,,1,,,,NO,NO,1,C:\FMEData\Resources\DesktopAdvanced\CommunityMapAdvancedSchema.xlsx,"0,0,1,3",Sheet1,NO,NO
    XLSXR_SCHEMA_HANDLING_REVISION = 2
    XLSXR_SKIP_EMPTY_ROWS = YES
    XLSXR_STRIP_SHEETNAME_SPACES = YES
    XLSXR_TABLELIST = Sheet2
    XLSXR_TRIM_ATTR_NAME_WHITESPACE = Yes
    XLSXR_USE_CUSTOM_SCHEMA = NO
    MAPPED -> DYNAMIC (writer GML_2)
NewFeatureType (writer GML_3)
Creator_2
    GEOMTYPE = Geometry Object
    NUM = 1

Bookmark: Reader Feature Types
Note: FireHalls [GML]
FireHalls (reader GML_1)
    attributes: HallNumber xml_char(30), Name xml_char(30), Address xml_char(30), PhoneNumber xml_char(30), Engine xml_char(1), Ladder xml_char(1), Quint xml_char(1), Rescue xml_char(1), Medic xml_char(1), gml_pointProperty xml_geometry, gml_multiPointProperty xml_geometry
    -> SchemaMapper
Note: Parks [MITAB]
Parks (reader MITAB_1)
    attributes: ParkId smallint, RefParkId smallint, ParkName char(40), NeighborhoodName char(40), VisitorCount smallint, TreeCount smallint, DogPark char(1), Washrooms char(1), SpecialFeatures char(1)
    -> SchemaMapper
Note: Zones [MITAB]
Zones (reader MITAB_2)
    attributes: ZoneName char(30), ZoneCategory char(30)
    -> SchemaMapper

Bookmark: Writer Feature Types
DYNAMIC (writer GML_2)

Bookmark: Parks and Zones
Creator
    GEOMTYPE = Geometry Object
    NUM = 1
    CREATED -> FeatureReader [INITIATOR]
FeatureReader
    ATTR_ACCUM_MODE = Only Use Result
    COMBINE_GEOM = Use Result
    DATASET = ""https://s3.amazonaws.com/FMEData/FMEData/Data/Zoning.zip" "https://s3.amazonaws.com/FMEData/FMEData/Data/Parks.zip""
    FORMAT = MITAB
    INTERACT = NONE
    MITAB_ENCODED_ATTRS = mapinfo_text_string
    MITAB_ENCODING = fme-source-encoding
    MITAB_UNENCODED_ATTR_PREFIX = fme_ mapinfo_
    MITAB_USE_SEARCH_ENVELOPE = NO
    MITAB__MITAB_FULL_ENHANCED_GEOMETRY = YES
    OUTPUT_FEATURES_DISPLAY = Schema and Data Features
    <SCHEMA> -> NewFeatureType (writer GML_3)
    <OTHER> -> NewFeatureType (writer GML_3)
