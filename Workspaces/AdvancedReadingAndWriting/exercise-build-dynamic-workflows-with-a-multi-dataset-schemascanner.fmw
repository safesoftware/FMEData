FME workspace exercise-build-dynamic-workflows-with-a-multi-dataset-schemascanner.fmw

Parameters:
- SourceDataset_CSV2 = https://s3.amazonaws.com/FMEData/FMEData/Resources/DynamicWorkflows/Data/Cedar%20Cottage.csv   # Source CSV (Comma Separated Value) File(s)
- FEATURE_TYPES =   # Feature Types to Read
- DestDataset_CSV2 = C:\FMEData\Output\Training   # Destination CSV (Comma Separated Value) Folder

Readers:
- CSV2_1: CSV2 from $(SourceDataset_CSV2)

Writers:
- CSV2_2: CSV2 to $(DestDataset_CSV2)

AttributeManager
    ATTR_TABLE:
      SET_TO Hours (varchar(200)) = @Value(Open)-@Value(Close)
      REMOVE Open (varchar(7))
      REMOVE Close (varchar(7))
    -> SchemaScanner
SchemaScanner
    CASE = No
    EMPTY_ATTR_HANDLING = IGNORE
    HOLD = Yes
    IGNORE_REGEXP = fme_<pipe>csv_<pipe>multi_
    INCLUDE_FORMAT_ATTR = Yes
    NUMERIC_ALLOW_LEADING_ZEROES = Yes
    SCHEMA_NAME_ATTR = fme_feature_type_name
    UNBOUNDED_NUMBERS = Yes
    UNBOUNDED_STRINGS = No
    -> DYNAMIC (writer CSV2_2)
    <SCHEMA> -> DYNAMIC (writer CSV2_2)

Bookmark: Reader Feature Types
CSV (reader CSV2_1)
    attributes: MarketType varchar(21), MarketName varchar(48), MergedAddress varchar(33), Day varchar(9), Open varchar(7), Close varchar(7), Months varchar(12), NumberOfVendors varchar(10)
    -> AttributeManager

Bookmark: Writer Feature Types
DYNAMIC (writer CSV2_2)
