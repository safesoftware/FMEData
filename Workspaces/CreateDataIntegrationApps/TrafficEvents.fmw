FME workspace TrafficEvents.fmw

Parameters:
- date = 20260930   # Filter by Date
- event_type = HAZARD   # Construction,ROAD_CONSTRUCTION%Poor Visibility,POOR_VISIBILITY Filter by Event Type
- region = drivebc.ca/1
- DestDataset_HTML = C:\FMEData\Output\map.html   # Destination Html File

Writers:
- HTML_1: HTML to $(DestDataset_HTML)

HTML (writer HTML_1)
    attributes: html_content buffer

Bookmark: Data extraction
Note: Make request to DriveBC's Open511 API
OpenAPICaller
    CLIENT_CERTIFICATE_TYPE = NONE
    CONNECTION_TIMEOUT_LENGTH = 60
    ENDPOINT_SELECTOR_SETTINGS = API_SOURCE,https://raw.githubusercontent.com/bcgov/api-specs/master/open511/open511_OAS3.json,ENDPOINT,/events,GET,PREVIEW_HEADER_GROUP,<Unused>,PREVIEW_HEADER_TABLE,<Unused>,PREVIEW_PATH_GROUP,<Unused>,PREVIEW_PATH_TABLE,<Unused>,PREVIEW_QUERY_GROUP,FME_DISCLOSURE_OPEN,PREVIEW_QUERY_TABLE,format String "The format of the response" status String "Limits the response to events having a given status." severity String "Limits the response to events tagged with one of the listed severity values. The possible values are: [MINOR, MODERATE, MAJOR].  Multiple values may be listed, and should be separated by a comma. The default is to return events of any severity." jurisdiction String "Limits the response to events reported by a given jurisdiction. The value given must be specified as the ID of a jurisdiction returned by the /jurisdiction resource. The default is to return events from all jurisdictions." event_type String "Limits the response to events tagged with one of the listed event types.  The possible values include: [CONSTRUCTION, INCIDENT, SPECIAL_EVENT, WEATHER_CONDITION].  Multiple values may be listed, and should be separated by a comma. The default is to return events of all types." created String "Limits the response to events based on the date and time that the event was created (first recorded). The date/time must be specified in ISO 8601 format, and may be prefixed by one of the following operators [<, <=, >, >=] to indicate 'before', 'before or equal to', 'after' or 'after or equal to' respectively.  For example, >2013-12-01T12:00:00Z requests all events create after Dec. 1, 2015 at 12pm (noon) Coordinated Universal Time.  The default is to return events with any creation time." updated String "Limits the response to events based on the date and time that the event was last updated. The date/time must be specified in ISO 8601 format, and may be prefixed by one of the following operators [<, <=, >, >=] to indicate 'before', 'before or equal to', 'after' or 'after or equal to' respectively.  For example, >2013-12-01T12:00:00Z requests all events updated after Dec. 1, 2015 at 12pm (noon) Coordinated Universal Time. The default is to return events with any update time" road_name String "Limits the response to events on a given road as specified by the road name.  An example of a valid road name is 'Highway 1'. The default is to return events on all roads." area_id String "Limits the response to events within one of the specified areas.  An area must be specified as the ID of an item returned by the /areas resource. For example: an area_id of 'drivebc.ca/1' limits events to those within the Lower Mainland District.  The default is to return events in all areas." bbox String "Limits the response to events that fall within the specified geographical bounding box.  The bbox format must be '[min longitude],[min latitude],[max longitude],[max latitude]' with WGS84 coordinates.  For example: -123.45,48.99,-122.45,49.49.  The default is to return events in all geographical locations.",PREVIEW_SAMPLE_RESPONSE,<Unused>,PREVIEW_SAMPLE_RESPONSE_GROUP,<Unused>,STATUS_GROUP,FME_DISCLOSURE_OPEN
    ERROR_ATTR = _error
    FOLLOW_REDIRECTS = FOLLOW_WITH_GET
    FULL_URL = http://api.open511.gov.bc.ca//events?event_subtype=$(event_type)&area_id=$(region)&in_effect_on=@DateTimeFormat($(date),%Y-%m-%dT00:00),@DateTimeFormat($(date),%Y-%m-%dT23:59)&format=json&status=ACTIVE&limit=500
    HOST = http://api.open511.gov.bc.ca/
    HOST_CHOICES = http://api.open511.gov.bc.ca/,https://api.open511.gov.bc.ca/
    HTTP_METHOD = GET
    IMPORT_SPEC_VALUES = https://raw.githubusercontent.com/bcgov/api-specs/master/open511/open511_OAS3.json,/events,GET,"Lists road events"
    INPUT_PORT_CONNECTED = *
    MAX_HTTP_VERSION = HTTP_2
    MAX_TRANSFERS_IN_PROGRESS = 25
    MINIMUM_ENCRYPTION_LEVEL = OS_DEFAULT
    QUERY_PARAMETERS = event_subtype;$(event_type) area_id;$(region) in_effect_on;@DateTimeFormat($(date),%Y-%m-%dT00:00),@DateTimeFormat($(date),%Y-%m-%dT23:59) format;json status;ACTIVE limit;500
    REDIRECT_AUTH = ORIGINAL_DOMAIN_ONLY
    RESPONSE_HANDLING_MODE = save_response
    RESPONSE_TYPE = Attribute
    SAVE_FILE_LOOKUP = NO
    SPLIT_MULTIPART_DOWNLOADS = NO
    STATUS_CODE_ATTR = _http_status_code
    TARGET_ATTR = _response_body
    TARGET_ATTR_ENCODING = auto-detect
    TARGET_URL = http://api.open511.gov.bc.ca//events
    TEST_REQUEST_REQUEST_PARAMETERS = authConnection;<Unused> authEnabled;false authMethod;<Unused> authPassword;<Unused> authUsername;<Unused> contentType;<Unused> method;GET multipartContentType;<Unused> queryParams:format;json queryParams:status;ACTIVE requestUrl;http://api.open511.gov.bc.ca//events uploadData;<Unused> verifySslCert;Yes version;HTTP_2
    TEST_REQUEST_RESPONSE =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
    TEST_REQUEST_STATUS:
      HTTP/1.1 200 OK
      Download Size: 29407 bytes
      Total Transfer Time: 195 ms
    TRANSFER_TIMEOUT_LENGTH = 90
    USE_COOKIES = No
    USE_FRAGMENTER = __DISABLED__
    VERIFY_SSL_CERTIFICATES = Yes
    -> JSONFragmenter
JSONFragmenter
    EXPLODE_FORMAT = JSON
    EXTRACT_ATTR = Yes
    INPUT_PORT_CONNECTED = CONNECTED
    JSON_ATTR = _response_body
    JSON_QUERY = json["events"][*]
    NEW_ATTRIBUTES = created buffer description buffer event_type buffer severity buffer status buffer geography buffer event_subtypes buffer areas buffer
    READ_FROM_FILE = NO
    RECURSIVE = NO
    REJECT_EMPTY_LISTS = YES
    FRAGMENTS -> GeometryReplacer
Note: Generate geometries from GeoJSON
GeometryReplacer
    KIND = GEOJSON
    REMOVE_ATTRIBUTE = Yes
    SOURCE = @Value(geography)
    KIND_LONG = GeoJSON
    -> JSONExtractor

Bookmark: Clean up web map label data
JSONExtractor
    EXTRACT_QUERY_TABLE = areas json[0]["name"]
    INPUT_PORT_CONNECTED = CONNECTED
    JSON_DOCUMENT = @Value(areas)
    READ_FROM_FILE = NO
    EVALUATED -> JSONExtractor_2
JSONExtractor_2
    EXTRACT_QUERY_TABLE = event_subtypes json[0]
    INPUT_PORT_CONNECTED = CONNECTED
    JSON_DOCUMENT = @Value(event_subtypes)
    READ_FROM_FILE = NO
    EVALUATED -> StringCaseChanger
StringCaseChanger
    ATTRCHOICE = SELECTED
    ATTRLIST = event_subtypes event_type status severity
    CHANGE_TYPE = fulltitle
    -> StringReplacer
StringReplacer
    CASE = NO
    NO_MATCH = _FME_NO_OP_
    REGEXP = NO
    STR_REPLACE_TABLE = "event_subtypes _  "
    -> DateTimeConverter
DateTimeConverter
    DATETIME_ATTR = created
    OUT_FORMAT = %a %b %d, %Y %l:%M%p
    PASSTHROUGH = YES
    REPAIR_INPUT = YES
    -> AttributeCreator

Bookmark: Create web map
Note: Create the text that will be within the web map pop-ups.
AttributeCreator
    ATTR_TABLE:
      SET_TO _map_label (varchar(200)) = <h5>@Value(event_subtypes) (@Value(severity))</h5>
        <br>
        <b>Description:</b> @Value(description)
        <br><br>
        <b>Region:</b> @Value(areas)
        <br><br>
        <b>Created:</b> @Value(created)
    INPUT_PORT_CONNECTED = CONNECTED
    -> HTMLReportGenerator
Note: Generate the web map report with road alerts.
HTMLReportGenerator
    CONTENT_LIST = HTML MAP_ESRI HTML
    PAGE_CONFIG:
      HTML{{HTML;<style>
        body {
          margin: 0;
          background:
            radial-gradient(circle at top left, rgba(52, 152, 219, 0.08), transparent 35%),
            linear-gradient(180deg, #f8fafc 0%, #eef3f8 100%);
          font-family: -apple-system, BlinkMacSystemFont, "Segoe UI", Roboto, Arial, sans-serif;
          color: #1f2937;
          min-height: 100vh;
        }

        .report-shell {
          max-width: 1100px;
          margin: 40px auto 56px;
          padding: 0 20px;
        }

        .report-header {
          text-align: center;
          margin-bottom: 22px;
        }

        .report-eyebrow {
          display: inline-block;
          margin-bottom: 10px;
          padding: 6px 12px;
          border-radius: 999px;
          background: rgba(37, 99, 235, 0.08);
          color: #1d4ed8;
          font-size: 12px;
          font-weight: 700;
          letter-spacing: 0.06em;
          text-transform: uppercase;
        }

        .report-title {
          margin: 0 0 8px;
          font-size: 2rem;
          font-weight: 700;
          line-height: 1.15;
        }

        .report-subtitle {
          margin: 0 auto;
          max-width: 720px;
          color: #6b7280;
          font-size: 1rem;
          line-height: 1.6;
        }

        .map-panel {
          background: rgba(255, 255, 255, 0.9);
          border: 1px solid rgba(15, 23, 42, 0.08);
          border-radius: 22px;
          box-shadow: 0 18px 40px rgba(15, 23, 42, 0.10);
          overflow: hidden;
          backdrop-filter: blur(8px);
        }

        .map-panel-top {
          display: flex;
          justify-content: space-between;
          align-items: center;
          gap: 16px;
          padding: 18px 22px;
          border-bottom: 1px solid rgba(15, 23, 42, 0.08);
          background: linear-gradient(180deg, rgba(255,255,255,0.95), rgba(248,250,252,0.95));
        }

        .map-panel-heading {
          margin: 0;
          font-size: 1.05rem;
          font-weight: 600;
        }

        .map-panel-note {
          margin: 4px 0 0;
          color: #6b7280;
          font-size: 0.92rem;
        }

        .map-badge {
          white-space: nowrap;
          padding: 8px 12px;
          border-radius: 999px;
          background: #eff6ff;
          color: #1d4ed8;
          font-size: 12px;
          font-weight: 700;
          border: 1px solid rgba(37, 99, 235, 0.12);
        }

        .map-frame {
          padding: 20px;
        }

        /* This centers the map visually by constraining it inside the card */
        #mapHTMLReportGenerator1 {
          width: 100% !important;
          max-width: 940px;
          height: 560px !important;
          margin: 0 auto;
          border-radius: 16px;
          overflow: hidden;
          box-shadow: inset 0 0 0 1px rgba(15, 23, 42, 0.06);
        }

        .report-footer {
          margin-top: 16px;
          text-align: center;
          color: #94a3b8;
          font-size: 1rem;
        }

        @media (max-width: 768px) {
          .report-shell {
            margin-top: 24px;
            padding: 0 14px;
          }

          .report-title {
            font-size: 1.6rem;
          }

          .map-panel-top {
            flex-direction: column;
            align-items: flex-start;
          }

          #mapHTMLReportGenerator1 {
            height: 420px !important;
          }
        }
      </style>

      <div class="report-shell">
        <div class="report-header">
          <div class="report-eyebrow">DriveBC</div>
          <h1 class="report-title">Road Alerts</h1>
          <p class="report-subtitle">
            Interactive map of current incidents, closures, and travel advisories across B.C.
          </p>
        </div>

        <section class="map-panel">
          <div class="map-panel-top">
            <div>
              <h2 class="map-panel-heading">Interactive Map</h2>
              <p class="map-panel-note">Pan, zoom, and select features to inspect details.</p>
            </div>
            <div class="map-badge">Powered by FME</div>
          </div>
          <div class="map-frame">;FME_CONTROLLER_QUERY_FILE;transformers/dependencies/html5/Custom HTML.fme;FME_CONTROLLER_CHOICE;Custom HTML}}MAP_ESRI{{LABEL;_map_label;HTML_ESCAPE_LABEL;no;COLOR;0,0,255;BASEMAP;Streets;URLS;;FME_CONTROLLER_QUERY_FILE;transformers/dependencies/html5/Map (Esri Leaflet).fme;FME_CONTROLLER_CHOICE;Map (Esri Leaflet)}}HTML{{HTML;    </div>
        </section>

        <div class="report-footer">
          The data used here originates from data made available by the <a href="https://www2.gov.bc.ca/gov/content/data/policy-standards/data-policies/open-data/open-government-licence-bc" target="_blank">British Columbia Government</a>. It contains information licensed under the Open Government License - British Columbia.
        </div>
      </div>;FME_CONTROLLER_QUERY_FILE;transformers/dependencies/html5/Custom HTML.fme;FME_CONTROLLER_CHOICE;Custom HTML}}
    -> HTML (writer HTML_1)
