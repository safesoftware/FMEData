FME workspace FoodVendorBusinesses.fmw
Title: MULTI to MULTI

Parameters:
- NEIGHBORHOOD =   # Pleasant"%"West End" Select a Neighborhood

Readers:
- CSV2_2: CSV2 from https://s3.amazonaws.com/FMEData/FMEData/Resources/FMEAccelerator/data/food-vendors.csv in LL84
- SQLITE3_2: SQLITE3 from https://s3.amazonaws.com/FMEData/FMEData/Data/Planning/business-licences-sqlite.zip

Writers:
- XLSXW_1: XLSXW to C:\FMEData\Output\FoodVendors.xlsx
- HTML_1: HTML to C:\FMEData\Output\FoodVendorsDataPreview.html

Bookmark: Source Data
Note: Food vendors
CSV (reader CSV2_2)
    attributes: KEY varchar(5), VENDOR_TYPE varchar(12), STATUS varchar(5), BUSINESS_NAME varchar(29), LOCATION varchar(76), DESCRIPTION varchar(35), GEO_LOCALAREA varchar(25), x x_coordinate, y y_coordinate
    -> AttributeValidator
Note: Business Licences SQLite
business-licences (reader SQLITE3_2)
    attributes: FOLDERYEAR integer, LicenceRSN integer, LicenceNumber varchar(10), LicenceRevisionNumber integer, BusinessName varchar(89), BusinessTradeName varchar(77), Status varchar(21), IssuedDate varchar(26), ExpiredDate varchar(11), BusinessType varchar(41), BusinessSubType varchar(35), Unit varchar(11), UnitType varchar(6), House varchar(9), Street varchar(21), City varchar(10), Province varchar(3), Country varchar(3), PostalCode varchar(11), LocalArea varchar(25), NumberofEmployees float, FeePaid integer, ExtractDate varchar(26), Geom varchar(72)
    -> Tester

Bookmark: Validate Food Truck Data
AttributeValidator
    TABLE = KEY$ATTRIBUTE_UNIQUE$<Unused>/BUSINESS_NAME$ATTRIBUTE_HAS_A_VALUE$<Unused>
    PASSED -> FeatureJoiner [LEFT]

Bookmark: Get Current License Data
Note: Only valid licenses
Tester
    BOOL_OP = COMPOSITE
    COMPOSITE_TEST = 1 AND 2
    TEST_CLAUSE:
      TEST @Value(Status) != Gone Out of Business
      TEST @Value(BusinessSubType) = Street Vendor
    TEST_MODE = TEST
    PASSED -> FeatureJoiner [RIGHT]

Bookmark: Join Data and Manage Attributes
FeatureJoiner
    ATTR_CONFLICT_RES_LOOKUP = USE_LEFT
    GEOMETRY_HANDLING_LOOKUP = USE_LEFT
    JOIN_KEYS = BUSINESS_NAME BusinessTradeName AUTO
    JOIN_MODE = Inner
    ATTR_CONFLICT_RES = Prefer Left
    GEOMETRY_HANDLING = Prefer Left
    JOINED -> AttributeManager
AttributeManager
    ATTR_TABLE:
      RENAME_SET_VALUE BUSINESS_NAME > Business Name (varchar(29))
      RENAME_SET_VALUE DESCRIPTION > Description (varchar(35))
      RENAME_SET_VALUE LOCATION > Location (varchar(76))
      RENAME_SET_VALUE STATUS > Status (varchar(5))
      REMOVE KEY (varchar(5))
      REMOVE FOLDERYEAR (int64)
      REMOVE LicenceRSN (int64)
      RENAME_SET_VALUE LicenceNumber > Business License Number (varchar(10))
      REMOVE LicenceRevisionNumber (int64)
      REMOVE BusinessName (varchar(89))
      REMOVE BusinessTradeName (varchar(77))
      REMOVE IssuedDate (varchar(26))
      REMOVE ExpiredDate (varchar(11))
      REMOVE Unit (varchar(11))
      REMOVE UnitType (varchar(6))
      REMOVE House (varchar(9))
      REMOVE Street (varchar(21))
      REMOVE City (varchar(10))
      REMOVE Province (varchar(3))
      REMOVE Country (varchar(3))
      REMOVE PostalCode (varchar(11))
      REMOVE LocalArea (varchar(25))
      REMOVE NumberofEmployees (real64)
      REMOVE FeePaid (int64)
      REMOVE ExtractDate (varchar(26))
      REMOVE Geom (varchar(72))
      REMOVE x (real64)
      REMOVE y (real64)
    -> Tester_2

Bookmark: Filter Neighborhood
Tester_2
    BOOL_OP = OR
    TEST_CLAUSE = CASE_INSENSITIVE_TEST @Value(GEO_LOCALAREA) = $(NEIGHBORHOOD)
    TEST_MODE = TEST
    PASSED -> Sheet1 (writer XLSXW_1)
    PASSED -> HTMLReportGenerator

Bookmark: Write CSV
Sheet1 (writer XLSXW_1)
    attributes: Business Name string(29), VENDOR_TYPE string(12), Description string(35), Location string(76), GEO_LOCALAREA string(25), Business License Number string(10), Status string(21), BusinessType string(41), BusinessSubType string(35)

Bookmark: Create Data Preview HTML Report
HTMLReportGenerator
    CONTENT_LIST = HEADER TABLE HTML
    PAGE_CONFIG:
      HEADER{{TEXT;Food Vendors in $(NEIGHBORHOOD);HEADER;H1;HEADER_ID;;ALIGNMENT;CENTER;COLOR;0,0,127;FME_CONTROLLER_QUERY_FILE;transformers/dependencies/html5/Header.fme;FME_CONTROLLER_CHOICE;Header}}TABLE{{STYLE;STRIPED;TABLE;Business Name|Business Name /Business License Number|License Number/Location|Location Accessibility/Status|Status /Description|Food Description;FME_CONTROLLER_QUERY_FILE;transformers/dependencies/html5/Table.fme;FME_CONTROLLER_CHOICE;Table}}HTML{{HTML;<style>

      h1 {
      font-family: 'Helvetica';
      font-weight: bold;
      padding: 10px;
      margin: 10px;
      }

      table {
      margin-left: 30px;
      margin-right: 30px;
      margin-top: 30px;
      margin-bottom:30px;
      }

      td {
      width: 0.1%;
      white-space: nowrap;
      }

      tr{
      font-family: 'Helvetica';
      color: darkslategray;
      background-color: #f5f5f5;
      }

      th {
      background-color: midnightBlue;
      font-family: 'Helvetica';
      color: gold;
      }

      tr:hover {
      background-color: lightgrey;
      font-size: 20px;
      }

      a:link {
      background-color: gold;
      border-radius: 5px;
      text-align: center;
      padding: 15px; 25px;
      color: midnightBlue;
      text-decoration: none;
      display: inline-block;
      }

      a:hover {
      color: goldenrod;
      background-color: midnightBlue;
      font-size: 18px;
      }

      p {
      text-align:center;
      }

      </style>

      <body>
      <p><a href="<your webhook url>">Download Excel Sheet</a></p>
      </body>;FME_CONTROLLER_QUERY_FILE;transformers/dependencies/html5/Custom HTML.fme;FME_CONTROLLER_CHOICE;Custom HTML}}
    TITLE = Food Vendor Businesses
    -> HTML (writer HTML_1)
HTML (writer HTML_1)
    attributes: html_content buffer
