FME workspace TrafficDynamicParameters.fmw

Parameters:
- DestDataset_JSON = drivebc-parameters.json   # Destination JSON (JavaScript Object Notation) File

Writers:
- JSON_1: JSON to $(DestDataset_JSON)

parameters (writer JSON_1)
    attributes: name string, defaultValue string, choices{}.display string, choices{}.value string

Bookmark: Create choice options for event types
OpenAPICaller_2
    CLIENT_CERTIFICATE_TYPE = NONE
    CONNECTION_TIMEOUT_LENGTH = 60
    ENDPOINT_SELECTOR_SETTINGS = API_SOURCE,https://raw.githubusercontent.com/bcgov/api-specs/master/open511/open511_OAS3.json,ENDPOINT,/events,GET,PREVIEW_HEADER_GROUP,<Unused>,PREVIEW_HEADER_TABLE,<Unused>,PREVIEW_PATH_GROUP,<Unused>,PREVIEW_PATH_TABLE,<Unused>,PREVIEW_QUERY_GROUP,FME_DISCLOSURE_OPEN,PREVIEW_QUERY_TABLE,format String "The format of the response" status String "Limits the response to events having a given status." severity String "Limits the response to events tagged with one of the listed severity values. The possible values are: [MINOR, MODERATE, MAJOR].  Multiple values may be listed, and should be separated by a comma. The default is to return events of any severity." jurisdiction String "Limits the response to events reported by a given jurisdiction. The value given must be specified as the ID of a jurisdiction returned by the /jurisdiction resource. The default is to return events from all jurisdictions." event_type String "Limits the response to events tagged with one of the listed event types.  The possible values include: [CONSTRUCTION, INCIDENT, SPECIAL_EVENT, WEATHER_CONDITION].  Multiple values may be listed, and should be separated by a comma. The default is to return events of all types." created String "Limits the response to events based on the date and time that the event was created (first recorded). The date/time must be specified in ISO 8601 format, and may be prefixed by one of the following operators [<, <=, >, >=] to indicate 'before', 'before or equal to', 'after' or 'after or equal to' respectively.  For example, >2013-12-01T12:00:00Z requests all events create after Dec. 1, 2015 at 12pm (noon) Coordinated Universal Time.  The default is to return events with any creation time." updated String "Limits the response to events based on the date and time that the event was last updated. The date/time must be specified in ISO 8601 format, and may be prefixed by one of the following operators [<, <=, >, >=] to indicate 'before', 'before or equal to', 'after' or 'after or equal to' respectively.  For example, >2013-12-01T12:00:00Z requests all events updated after Dec. 1, 2015 at 12pm (noon) Coordinated Universal Time. The default is to return events with any update time" road_name String "Limits the response to events on a given road as specified by the road name.  An example of a valid road name is 'Highway 1'. The default is to return events on all roads." area_id String "Limits the response to events within one of the specified areas.  An area must be specified as the ID of an item returned by the /areas resource. For example: an area_id of 'drivebc.ca/1' limits events to those within the Lower Mainland District.  The default is to return events in all areas." bbox String "Limits the response to events that fall within the specified geographical bounding box.  The bbox format must be '[min longitude],[min latitude],[max longitude],[max latitude]' with WGS84 coordinates.  For example: -123.45,48.99,-122.45,49.49.  The default is to return events in all geographical locations.",PREVIEW_SAMPLE_RESPONSE,<Unused>,PREVIEW_SAMPLE_RESPONSE_GROUP,<Unused>,STATUS_GROUP,FME_DISCLOSURE_OPEN
    ERROR_ATTR = _error
    FOLLOW_REDIRECTS = FOLLOW_WITH_GET
    FULL_URL = http://api.open511.gov.bc.ca//events?format=json&status=ACTIVE&limit=500
    HOST = http://api.open511.gov.bc.ca/
    HOST_CHOICES = http://api.open511.gov.bc.ca/,https://api.open511.gov.bc.ca/
    HTTP_METHOD = GET
    IMPORT_SPEC_VALUES = https://raw.githubusercontent.com/bcgov/api-specs/master/open511/open511_OAS3.json,/events,GET,"Lists road events"
    INPUT_PORT_CONNECTED = *
    MAX_HTTP_VERSION = HTTP_2
    MAX_TRANSFERS_IN_PROGRESS = 25
    MINIMUM_ENCRYPTION_LEVEL = OS_DEFAULT
    QUERY_PARAMETERS = format;json status;ACTIVE limit;500
    REDIRECT_AUTH = ORIGINAL_DOMAIN_ONLY
    RESPONSE_HANDLING_MODE = save_response
    RESPONSE_TYPE = Attribute
    SAVE_FILE_LOOKUP = NO
    SPLIT_MULTIPART_DOWNLOADS = NO
    STATUS_CODE_ATTR = _http_status_code
    TARGET_ATTR = _response_body
    TARGET_ATTR_ENCODING = auto-detect
    TARGET_URL = http://api.open511.gov.bc.ca//events
    TEST_REQUEST_REQUEST_PARAMETERS = authConnection;<Unused> authEnabled;false authMethod;<Unused> authPassword;<Unused> authUsername;<Unused> contentType;<Unused> method;GET multipartContentType;<Unused> queryParams:format;json queryParams:status;ACTIVE requestUrl;http://api.open511.gov.bc.ca//events uploadData;<Unused> verifySslCert;Yes version;HTTP_2
    TEST_REQUEST_RESPONSE =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
    TEST_REQUEST_STATUS:
      HTTP/1.1 200 OK
      Download Size: 29407 bytes
      Total Transfer Time: 195 ms
    TRANSFER_TIMEOUT_LENGTH = 90
    USE_COOKIES = No
    USE_FRAGMENTER = __DISABLED__
    VERIFY_SSL_CERTIFICATES = Yes
    -> JSONFragmenter
JSONFragmenter
    EXPLODE_FORMAT = JSON
    EXTRACT_ATTR = Yes
    INPUT_PORT_CONNECTED = CONNECTED
    JSON_ATTR = _response_body
    JSON_QUERY = json["events"][*]
    NEW_ATTRIBUTES = +ivr_message buffer created buffer description buffer event_type buffer severity buffer status buffer updated buffer geography buffer event_subtypes buffer schedule buffer areas buffer
    READ_FROM_FILE = NO
    RECURSIVE = NO
    REJECT_EMPTY_LISTS = YES
    FRAGMENTS -> AttributeKeeper_2
AttributeKeeper_2
    CREATE_BULK_MODE_FEATURES = NO
    KEEP_ATTRS = event_subtypes
    -> JSONExtractor
JSONExtractor
    EXTRACT_QUERY_TABLE = event_subtypes json[0]
    INPUT_PORT_CONNECTED = CONNECTED
    JSON_DOCUMENT = @Value(event_subtypes)
    READ_FROM_FILE = NO
    EVALUATED -> Sampler
    <REJECTED> -> Logger
Sampler
    GROUP_BY = event_subtypes
    MODE = ORIGINAL
    RATE = 1
    SAMPLE_TYPE_MULTIPLIER = -1
    SAMPLE_MODE = No
    SAMPLE_TYPE_LONG = First N Features
    SAMPLED -> AttributeCopier
AttributeManager_2
    ATTR_TABLE = RENAME_SET_VALUE event_subtypes > value (buffer)
    -> ListBuilder_2
ListBuilder_2
    LIST_ATTRS_TO_INCLUDE = display value
    LIST_NAME = choices
    -> ListSorter_2
ListSorter_2
    ORDER = Ascending
    SRC_LIST = choices{}.display
    TYPE = Alphabetic
    -> AttributeCreator_3
AttributeCreator_3
    ATTR_TABLE:
      SET_TO name (varchar(10)) = event_type
      SET_TO defaultValue (varchar(19)) = HAZARD
    INPUT_PORT_CONNECTED = CONNECTED
    -> parameters (writer JSON_1)
Note: Missing event subtype
Logger
    LOG_FEATURE = LOG_ONLY
    MAXCOORDS = 20
    MAXFEATS = 20
    MESSAGE = Feature is:
    SEVERITY = WARN

Bookmark: Clean up display values
AttributeCopier
    ATTR_TABLE = COPY event_subtypes > display
    MISSING_INPUT_ATTRS = REMOVE
    -> StringReplacer
StringReplacer
    CASE = NO
    NO_MATCH = _FME_NO_OP_
    REGEXP = NO
    STR_REPLACE_TABLE = "display _  "
    -> StringCaseChanger
StringCaseChanger
    ATTRCHOICE = SELECTED
    ATTRLIST = display
    CHANGE_TYPE = fulltitle
    -> AttributeManager_2

Bookmark: Create choice options for geographic regions
OpenAPICaller
    CLIENT_CERTIFICATE_TYPE = NONE
    CONNECTION_TIMEOUT_LENGTH = 60
    ENDPOINT_SELECTOR_SETTINGS = API_SOURCE,https://raw.githubusercontent.com/bcgov/api-specs/master/open511/open511_OAS3.json,ENDPOINT,/areas,GET,PREVIEW_HEADER_GROUP,<Unused>,PREVIEW_HEADER_TABLE,<Unused>,PREVIEW_PATH_GROUP,<Unused>,PREVIEW_PATH_TABLE,<Unused>,PREVIEW_QUERY_GROUP,FME_DISCLOSURE_OPEN,PREVIEW_QUERY_TABLE,format String "The format of the response",PREVIEW_SAMPLE_RESPONSE,<Unused>,PREVIEW_SAMPLE_RESPONSE_GROUP,<Unused>,STATUS_GROUP,FME_DISCLOSURE_OPEN
    ERROR_ATTR = _error
    FOLLOW_REDIRECTS = FOLLOW_WITH_GET
    FULL_URL = http://api.open511.gov.bc.ca//areas?format=json
    HOST = http://api.open511.gov.bc.ca/
    HOST_CHOICES = http://api.open511.gov.bc.ca/,https://api.open511.gov.bc.ca/
    HTTP_METHOD = GET
    IMPORT_SPEC_VALUES = https://raw.githubusercontent.com/bcgov/api-specs/master/open511/open511_OAS3.json,/areas,GET,"Lists the geographical areas (e.g. districts) that can be used to filter events."
    INPUT_PORT_CONNECTED = *
    JSON_QUERY = json["areas"][*]
    MAX_HTTP_VERSION = HTTP_2
    MAX_TRANSFERS_IN_PROGRESS = 25
    MINIMUM_ENCRYPTION_LEVEL = OS_DEFAULT
    QUERY_PARAMETERS = format;json
    REDIRECT_AUTH = ORIGINAL_DOMAIN_ONLY
    RESPONSE_HANDLING_MODE = json_fragments
    SPLIT_MULTIPART_DOWNLOADS = NO
    STATUS_CODE_ATTR = _http_status_code
    TARGET_URL = http://api.open511.gov.bc.ca//areas
    TEMP_JSON_FILEPATH = /var/folders/_8/3yw38v3s5w7brzpd2m22dnh40000gp/T/fme_testRequestPreviewResults.FQEkFB
    TEST_REQUEST_REQUEST_PARAMETERS = authConnection;<Unused> authEnabled;false authMethod;<Unused> authPassword;<Unused> authUsername;<Unused> contentType;<Unused> method;GET multipartContentType;<Unused> queryParams:format;json requestUrl;http://api.open511.gov.bc.ca//areas uploadData;<Unused> verifySslCert;Yes version;HTTP_2
    TEST_REQUEST_RESPONSE = { 	"areas": [ 		{ 			"id": "drivebc.ca/1", 			"name": "Lower Mainland District", 			"url": "http://www.geonames.org/8630136" 		}, 		{ 			"id": "drivebc.ca/2", 			"name": "Vancouver Island District", 			"url": "http://www.geonames.org/8630140" 		}, 		{ 			"id": "drivebc.ca/3", 			"name": "Rocky Mountain District", 			"url": "http://www.geonames.org/8630135" 		}, 		{ 			"id": "drivebc.ca/4", 			"name": "West Kootenay District", 			"url": "http://www.geonames.org/8630139" 		}, 		{ 			"id": "drivebc.ca/5", 			"name": "Okanagan-Shuswap District", 			"url": "http://www.geonames.org/8630138" 		}, 		{ 			"id": "drivebc.ca/6", 			"name": "Thompson-Nicola District", 			"url": "http://www.geonames.org/8630137" 		}, 		{ 			"id": "drivebc.ca/7", 			"name": "Cariboo District", 			"url": "http://www.geonames.org/8630134" 		}, 		{ 			"id": "drivebc.ca/8", 			"name": "Peace District", 			"url": "http://www.geonames.org/8630130" 		}, 		{ 			"id": "drivebc.ca/9", 			"name": "Fort George District", 			"url": "http://www.geonames.org/8630131" 		}, 		{ 			"id": "drivebc.ca/10", 			"name": "Bulkley Stikine District", 			"url": "http://www.geonames.org/8630133" 		}, 		{ 			"id": "drivebc.ca/11", 			"name": "Skeena District", 			"url": "http://www.geonames.org/8630132" 		} 	], 	"meta": { 		"up_url": "", 		"url": "/areas", 		"version": "v1" 	}, 	"pagination": { 		"offset": 0 	} }
    TEST_REQUEST_STATUS:
      HTTP/1.1 200 OK
      Download Size: 380 bytes
      Total Transfer Time: 212 ms
    TRANSFER_TIMEOUT_LENGTH = 90
    USE_COOKIES = No
    USE_FRAGMENTER = *
    VERIFY_SSL_CERTIFICATES = Yes
    -> AttributeExposer
AttributeExposer
    ATTR_TABLE = id,,name,
    -> AttributeKeeper
AttributeKeeper
    CREATE_BULK_MODE_FEATURES = NO
    KEEP_ATTRS = id,name
    -> AttributeManager
AttributeManager
    ATTR_TABLE:
      RENAME_SET_VALUE name > display (buffer)
      RENAME_SET_VALUE id > value (varchar(200))
    USER_EXPOSED_ATTRIBUTES = _response_body
    -> ListBuilder
ListBuilder
    LIST_ATTRS_TO_INCLUDE = display value
    LIST_NAME = choices
    -> ListSorter
ListSorter
    ORDER = Ascending
    SRC_LIST = choices{}.display
    TYPE = Alphabetic
    -> AttributeCreator_2
AttributeCreator_2
    ATTR_TABLE:
      SET_TO name (varchar(6)) = region
      SET_TO defaultValue (varchar(200))
    INPUT_PORT_CONNECTED = CONNECTED
    -> parameters (writer JSON_1)

Bookmark: Set date parameter to today's date
Creator
    GEOMTYPE = Geometry Object
    NUM = 1
    CREATED -> AttributeCreator
AttributeCreator
    ATTR_TABLE:
      SET_TO name (varchar(4)) = date
      SET_TO defaultValue (varchar(200)) = @DateTimeNow()
    INPUT_PORT_CONNECTED = CONNECTED
    -> parameters (writer JSON_1)
