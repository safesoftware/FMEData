FME workspace exercise-publish-data-with-a-workspace.fmwt
Title: exercise-publish-data-with-a-workspace

Parameters:
- SourceDataset_OGCKML = $(FME_MF_DIR)1/Boundaries/VancouverNeighborhoods.kml   # Source Google KML File or URL
- SourceDataset_GML = $(FME_MF_DIR)1/Elections/ElectionVoting.gml   # Source Geography Markup Language (GML) File(s)
- DestDataset_FILEGDB = C:\FMEData\Output\Training\DepartmentData.gdb   # File Geodatabase

Readers:
- OGCKML_1: OGCKML from $(SourceDataset_OGCKML)
- GML_1: GML from $(SourceDataset_GML)

Writers:
- FILEGDB_1: FILEGDB to $(DestDataset_FILEGDB)

VotingPlaces (reader GML_1)
    attributes: Division xml_char(3), Name xml_char(50), Number xml_char(4), Street xml_char(20), Room xml_char(30), gml_pointProperty xml_geometry, gml_multiPointProperty xml_geometry
    -> Clipper [CANDIDATE]
Neighborhoods (reader OGCKML_1)
    attributes: NeighborhoodId kml_buffer, NeighborhoodName kml_buffer, NeighborhoodURL kml_buffer, TotalPopulation2001 kml_buffer, TotalPopulation2011 kml_buffer
    -> Reprojector
Reprojector
    DEST = UTM83-10
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CLIPPER]
    REPROJECTED -> Neighborhoods (writer FILEGDB_1)
Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_PARTS
    MISSING_M_MODE_LOOKUP = LINEAR
    MISSING_Z_MODE_LOOKUP = LINEAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Linear Interpolation
    INSIDE -> VotingPlaces (writer FILEGDB_1)
VotingPlaces (writer FILEGDB_1)
    attributes: gml_id text(2048), gml_parent_id text(2048), gml_parent_property text(2048), Division text(3), Name text(50), Number text(4), Street text(20), Room text(30), gml_pointProperty text(2048), gml_multiPointProperty text(2048)
Neighborhoods (writer FILEGDB_1)
    attributes: NeighborhoodId text(2048), NeighborhoodName text(2048), NeighborhoodURL text(2048), TotalPopulation2001 text(2048), TotalPopulation2011 text(2048)
