FME workspace exercise-submit-job-through-webhook-url.fmwt
Title: MULTI to GEOJSON

Parameters:
- FEATURE_TYPES = Downtown Fairview Kitsilano Mount Pleasant Strathcona West End

Readers:
- SHAPEFILE_1: SHAPEFILE from $(FME_MF_DIR)1/311_service_request/311_service_request.shp
- SPATIALITE_NATIVE_1: SPATIALITE_NATIVE from $(FME_MF_DIR)2/Downloads/Neighbourhoods.sqlite

Writers:
- GEOJSON_1: GEOJSON to $(FME_MF_DIR)311-service-requests.geojson

Downtown (reader SPATIALITE_NATIVE_1)
    attributes: Neighborho varchar(254), Neighbor00 varchar(254), Neighbor01 varchar(254), TotalPopul varchar(254), TotalPop00 varchar(254)
    -> Reprojector
Reprojector
    DEST = LL84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CLIPPER]
311_service_request (reader SHAPEFILE_1)
    attributes: department varchar(254), service_re varchar(254), status varchar(254), closure_re varchar(254), service_00 varchar(254), service_01 varchar(254), last_modif varchar(254), address varchar(254), local_area varchar(254), channel varchar(254), latitude double, longitude double, geom varchar(254), ORIG_FID long
    -> GeometryFilter
GeometryFilter
    FILTER_MODE = SIMPLE
    FILTER_MULTI = FILTER_TYPES]Point]FME_CONTROLLER_QUERY_FILE]]FME_CONTROLLER_CHOICE]Simple
    Point -> Reprojector_2
Reprojector_2
    DEST = LL84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> 311Requests (writer GEOJSON_1)
311Requests (writer GEOJSON_1)
    attributes: department string, service_re string, status string, closure_re string, service_00 string, service_01 string, last_modif string, address string, local_area string, channel string, latitude float, longitude float, geom string, ORIG_FID int, _clipped string
