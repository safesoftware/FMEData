FME workspace 3.10-Design-PartialRunsDisabledObjects.fmw

Parameters:
- FEATURE_TYPES =
- SourceDataset_OGCKML = c:\FMEData\Data\Boundaries\VancouverNeighborhoods.kml   # Source Google KML File or URL
- SourceDataset_MITAB = c:\FMEData\Data\Parks\Parks.tab   # Source MapInfo TAB File(s)
- SourceDataset_GEOTIFF_2 = ""c:\FMEData\Data\Orthophotos\02-03-HI.tif" "c:\FMEData\Data\Orthophotos\02-03-JK.tif" "c:\FMEData\Data\Orthophotos\02-03-LM.tif" "c:\FMEData\Data\Orthophotos\02-03-NO.tif" "c:\FMEData\Data\Orthophotos\04-05-HI.tif" "c:\FMEData\Data\Orthophotos\04-05-JK.tif" "c:\FMEData\Data\Orthophotos\04-05-LM.tif" "c:\FMEData\Data\Orthophotos\04-05-NO.tif" "c:\FMEData\Data\Orthophotos\04-05-PQ.tif" "c:\FMEData\Data\Orthophotos\04-05-RS.tif" "c:\FMEData\Data\Orthophotos\06-07-HI.tif" "c:\FMEData\Data\Orthophotos\06-07-JK.tif" "c:\FMEData\Data\Orthophotos\06-07-LM.tif" "c:\FMEData\Data\Orthophotos\06-07-NO.tif" "c:\FMEData\Data\Orthophotos\06-07-PQ.tif" "c:\FMEData\Data\Orthophotos\06-07-RS.tif" "c:\FMEData\Data\Orthophotos\08-09-HI.tif" "c:\FMEData\Data\Orthophotos\08-09-JK.tif" "c:\FMEData\Data\Orthophotos\08-09-LM.tif" "c:\FMEData\Data\Orthophotos\08-09-NO.tif" "c:\FMEData\Data\Orthophotos\08-09-PQ.tif" "c:\FMEData\Data\Orthophotos\08-09-RS.tif" "c:\FMEData\Data\Orthophotos\10-11-HI.tif" "c:\FMEData\Data\Orthophotos\10-11-JK.tif" "c:\FMEData\Data\Orthophotos\10-11-LM.tif" "c:\FMEData\Data\Orthophotos\10-11-NO.tif" "c:\FMEData\Data\Orthophotos\10-11-PQ.tif" "c:\FMEData\Data\Orthophotos\10-11-RS.tif" "c:\FMEData\Data\Orthophotos\12-13-HI.tif" "c:\FMEData\Data\Orthophotos\12-13-JK.tif" "c:\FMEData\Data\Orthophotos\12-13-LM.tif" "c:\FMEData\Data\Orthophotos\12-13-NO.tif" "c:\FMEData\Data\Orthophotos\12-13-PQ.tif" "c:\FMEData\Data\Orthophotos\12-13-RS.tif" "c:\FMEData\Data\Orthophotos\14-15-HI.tif" "c:\FMEData\Data\Orthophotos\14-15-JK.tif" "c:\FMEData\Data\Orthophotos\14-15-LM.tif" "c:\FMEData\Data\Orthophotos\14-15-NO.tif" "c:\FMEData\Data\Orthophotos\14-15-PQ.tif" "c:\FMEData\Data\Orthophotos\14-15-RS.tif""   # Source GeoTIFF File(s)
- FEATURE_TYPES_2 =
- DestDataset_GEOTIFF = c:\FMEData\Output\Training   # Destination GeoTIFF Folder
- DestDataset_XLSXW = c:\FMEData\Output\Training\Neighborhoods.xlsx   # Destination Microsoft Excel File

Readers:
- XLSXR_2: XLSXR from c:\FMEData\Data\Culture\PublicArt.xlsx in LL84
- OGCKML_2: OGCKML from $(SourceDataset_OGCKML)
- MITAB_2: MITAB from $(SourceDataset_MITAB)
- GEOTIFF_3: GEOTIFF from $(SourceDataset_GEOTIFF_2)

Writers:
- GEOTIFF_1: GEOTIFF to $(DestDataset_GEOTIFF)
- XLSXW_2: XLSXW to $(DestDataset_XLSXW)

Note: Thsi workspace demonstrates how to run sections of a workspace by disabling certain objects/components. Demonstrate how to enable/disable objects and run the workspace to show how it will only run the top part of transformation.
Reprojector_2
    DEST = UTM83-10
    INTERPOLATION_TYPE_NAME = Nearest Neighbor
    RASTER_CELL_SIZE = Preserve Cells
    RASTER_TOLERANCE = 0.0
    SOURCE = Read from feature
    REPROJECTED -> Clipper [CLIPPER]

Bookmark: Parks
Parks (reader MITAB_2)
    attributes: ParkId smallint, RefParkId smallint, ParkName char(40), NeighborhoodName char(40), VisitorCount smallint, TreeCount smallint, DogPark char(1), Washrooms char(1), SpecialFeatures char(1)
    -> PointOnAreaOverlayer [AREA]

Bookmark: Public Art
Downtown (reader XLSXR_2)
    attributes: Name char(51), Title char(51), Longitude x_coordinate, Latitude y_coordinate
    -> VertexCreator

Bookmark: Create points and reproject
VertexCreator
    MEASURE_TYPE = Continuous
    MISSING_VAL_MODE = None (Drop Values)
    MODE_NAME = Add Point
    XVAL = @Value(Longitude)
    YVAL = @Value(Latitude)
    -> Reprojector
Reprojector
    DEST = UTM83-10
    INTERPOLATION_TYPE_NAME = Nearest Neighbor
    RASTER_CELL_SIZE = Preserve Cells
    RASTER_TOLERANCE = 0.0
    SOURCE = Read from feature
    REPROJECTED -> PointOnAreaOverlayer [POINT]

Bookmark: Overlay points on parks
PointOnAreaOverlayer
    ATTR_ACCUM_MODE = Merge Incoming
    ATTR_CONFLICT_RES = Use Original
    DEAGGREGATE_INPUT = Yes
    OV_ATTR = _overlaps
    POLYS_FIRST = NO
    AREA -> Tester
Tester
    BOOL_OP = OR
    TEST_CLAUSE = TEST @Value(_overlaps) = 0
    TEST_MODE = TEST
    PASSED -> VectorOnRasterOverlayer [VECTOR] [off]
    PASSED -> Sheet1 (writer XLSXW_2) [off]

Bookmark: GeoTIFF Writer
Sheet1 (writer XLSXW_2)
    attributes: ParkId number(20), RefParkId number(20), ParkName string(40), NeighborhoodName string(40), VisitorCount number(20), TreeCount number(20), DogPark string(1), Washrooms string(1), SpecialFeatures string(1)

Bookmark: Orthophotos
GEOTIFF (reader GEOTIFF_3) [off]
    -> RasterMosaicker

Bookmark: Combine orthophotos
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> VectorOnRasterOverlayer [RASTER]

Bookmark: Overlay parks on raster
VectorOnRasterOverlayer
    ALPHA = 1.0
    ANTI_ALIASING = No
    COMPOSITE_USING_ALPHA_BAND = No
    TOLERANCE = 0.5
    RASTER -> Clipper [CLIPPEE]

Bookmark: Neighborhoods
Neighborhoods (reader OGCKML_2) [off]
    attributes: NeighborhoodId kml_buffer, NeighborhoodName kml_buffer, NeighborhoodURL kml_buffer, TotalPopulation2001 kml_buffer, TotalPopulation2011 kml_buffer
    -> Reprojector_2

Bookmark: Clip raster to neighborhoods
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterSelector

Bookmark: Raster processing
RasterSelector
    BAND_LIST = ALL ALL
    SELECTION_MODE = Band and Palette List
    -> RasterBandNodataSetter
RasterBandNodataSetter
    NODATA_VALUE = 0
    REPLACE_CELL_VALUES = No
    -> Raster1 (writer GEOTIFF_1)

Bookmark: GeoTIFF Writer
Raster1 (writer GEOTIFF_1)
