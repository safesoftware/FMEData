FME workspace 5.07-BestPractice-BookmarksPerformance.fmw

Readers:
- FILEGDB_1: FILEGDB from C:\FMEData2018\Data\Addresses\Addresses.gdb
- XLSXR_1: XLSXR from C:\FMEData2018\Data\Emergency\crime_xlsx_all_years.zip

Note: Join Addresses and Crime Data
FeatureJoiner
    ATTR_CONFLICT_RES = Use Left
    GEOMETRY_HANDLING = Use Left
    JOIN_KEYS = JoinKey HUNDRED_BLOCK AUTO
    JOIN_MODE = Inner
    JOINED -> AttributeValueMapper
Note: Bookmarks for Performance / Turn on feature caching and run the workspace. Notice that every transformer in the Prepare Data bookmark is cached. / Collapse the bookmark and run again (run the full workspace). / Expand the bookmark. Notice that inside that bookmark only the AttributeManager_2 transformer was cached. / Not caching data can save time and resources (though not a huge amount in this example, because the amounts of data are small).
AttributeValueMapper
    DIRECTION = Forward (Source To Destination)
    LUT = Break and Enter Commercial,10,Break and Enter Residential/Other,10,Offence Against a Person,12,Other Theft,5,Theft from Vehicle,5,Theft of Bicycle,5,Theft of Vehicle,12,Vehicle Collision or Pedestrian Struck (with Fatality),15,Vehicle Collision or Pedestrian Struck (with Injury),10,Homicide,25,Mischief,2
    SRC = TYPE
    VAL_ATTR = CrimeValue
    -> Aggregator
Aggregator
    ACCUM_ATTRS_NAME = Use Attributes From One Feature
    AGGREGATE_TYPE = Homogeneous Collection (If Possible)
    COUNT_ATTR = NumberOfCrimes
    GROUP_BY = PSTLADDRESS
    MODE = Geometry - Assemble One Level
    ORDERED = No
    SEP = ,
    SUM = CrimeValue
    AGGREGATE -> CenterPointReplacer
CenterPointReplacer
    MODE = Center Point

Bookmark: Address Data
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> AttributeSplitter

Bookmark: Prepare Data for Matching
AttributeSplitter
    ATTR_NAME = PSTLADDRESS
    DELIMITER = " "
    DROP_EMPTY_PARTS = No
    LIST_NAME = _list
    TRIM_OPTION = Both
    -> AttributeManager
AttributeManager
    ATTR_TABLE:
      REMOVE OBJECTID
      REMOVE GlobalID
      REMOVE OWNERNM1
      REMOVE OWNERNM2
      RENAME_SET_VALUE PSTLCITY > City
      RENAME_SET_VALUE PSTLPROV > Province
      REMOVE INTSTATE
      REMOVE INTPSTLCD
      RENAME_SET_VALUE COUNTRY > Country
      REMOVE REPRESENT
      REMOVE STATUS
      REMOVE LASTUPDATE
      REMOVE LASTEDITOR
      RENAME_SET_VALUE POSTALCODE > PostalCode
      SET_TO Number = @Value(_list{0})
      SET_TO Street = @Value(_list{1}) @Value(_list{2}) @Value(_list{3})
    -> StringReplacer
StringReplacer
    CASE = NO
    FIND_TEXT = ..$
    NO_MATCH = _FME_NO_OP_
    REGEXP = YES
    REPLACE_TEXT = XX
    SRC_ATTRS = Number
    -> StringCaseChanger
StringCaseChanger
    ATTRCHOICE = Selected Attributes
    ATTRLIST = Street
    CHANGE_TYPE = UPPERCASE
    -> AttributeManager_2
Note: Create Join Key
AttributeManager_2
    ATTR_TABLE = SET_TO JoinKey = @Trim(@Value(Number) @Value(Street))
    -> FeatureJoiner [LEFT]

Bookmark: Crime Data
2017 (reader XLSXR_1)
    attributes: TYPE char(25), YEAR number(5,0), MONTH number(3,0), DAY number(3,0), HOUR number(3,0), MINUTE number(3,0), HUNDRED_BLOCK char(36), NEIGHBOURHOOD char(26), X x_coordinate, Y y_coordinate
    -> FeatureJoiner [RIGHT]
