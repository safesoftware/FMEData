FME workspace 5.17-BestPractice-KeyStageInspection.fmw
Title: Transformers-Ex1-Complete

Parameters:
- DestDataset_CSV2 = C:\FMEData2018\Output   # Destination CSV (Comma Separated Value) Folder

Writers:
- CSV2_1: CSV2 to $(DestDataset_CSV2)

Creator
    GEOMTYPE = Geometry Object
    NUM = 1
    CREATED -> FeatureReader [INITIATOR]
Note: Restricted to 200 features for performance reasons.
FeatureReader
    ATTRIBUTES = PostalAddress,"OBJECTID,GlobalID,OWNERNM1,OWNERNM2,PSTLADDRESS,PSTLCITY,PSTLPROV,INTSTATE,INTPSTLCD,COUNTRY,REPRESENT,STATUS,LASTUPDATE,LASTEDITOR,POSTALCODE",PostcodeBoundaries,"OBJECTID,CFSAUID,SHAPE_Length,SHAPE_Area"
    ATTR_ACCUM_MODE = Only Use Result
    COMBINE_GEOM = Use Result
    DATASET = C:\FMEData2018\Data\Addresses\Addresses.gdb
    FEATURETYPES = PostalAddress
    FILEGDB_QUERY_FEATURE_TYPES_FOR_MERGE_FILTERS = Yes
    FILEGDB_USE_SEARCH_ENVELOPE = NO
    FORMAT = FILEGDB
    INTERACT = <No Spatial Filter>
    MAX_FEATURES = 200
    OUTPUT_FEATURES_DISPLAY = Schema and Data Features
    PostalAddress -> AttributeSplitter
AttributeSplitter
    ATTR_NAME = PSTLADDRESS
    DELIMITER = " "
    DROP_EMPTY_PARTS = No
    LIST_NAME = _list
    TRIM_OPTION = Both
    -> AttributeManager
AttributeManager
    ATTR_TABLE:
      REMOVE OBJECTID
      REMOVE GlobalID
      RENAME_SET_VALUE OWNERNM1 > Owner1
      RENAME_SET_VALUE OWNERNM2 > Owner2
      RENAME_SET_VALUE PSTLCITY > City
      RENAME_SET_VALUE PSTLPROV > Province
      REMOVE INTSTATE
      REMOVE INTPSTLCD
      RENAME_SET_VALUE COUNTRY > Country
      REMOVE REPRESENT
      REMOVE STATUS
      REMOVE LASTUPDATE
      REMOVE LASTEDITOR
      RENAME_SET_VALUE POSTALCODE > PostalCode
      SET_TO Provider = Safe Software
      SET_TO UpdateDate = @DateTimeNow()
      SET_TO Number = @Value(_list{0})
      SET_TO Street = @Value(_list{1}) @Value(_list{2}) @Value(_list{3})
    -> PostalAddress (writer CSV2_1)
Note: Change the Writer encoding from DOS Latin-US to Unicode (UTF-8) to get the correct results. / fyi When running the workspace, the log window even tells us that is what the problem is!
Note: The point here is to demonstrate *where* to find a problem. We know the output is bad, but we don't know what caused it. Therefore we investigate from the start (inspect source data) through every aspect (read/transform/write) to find the issue.
PostalAddress (writer CSV2_1)
    attributes: Owner1 string, Owner2 string, Number string, Street string, City string, Province string, PostalCode string, Country string, Provider string, UpdateDate string
