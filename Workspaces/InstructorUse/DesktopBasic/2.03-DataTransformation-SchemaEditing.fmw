FME workspace 2.03-DataTransformation-SchemaEditing.fmw

Parameters:
- SourceDataset_FILEGDB = c:\FMEData\Data\CommunityMapping\CommunityMap.gdb   # File Geodatabase
- DestDataset_ESRISHAPE = c:\FMEData\Output\Training   # Destination Esri Shapefile Folder
- DestDataset_GML = c:\FMEData\Output\Training\Parks.gml   # Destination Geography Markup Language (GML) File

Readers:
- FILEGDB_1: FILEGDB from $(SourceDataset_FILEGDB)

Writers:
- ESRISHAPE_1: ESRISHAPE to $(DestDataset_ESRISHAPE)
- GML_1: GML to $(DestDataset_GML)

Note: A workspace to demonstrate schema editing. / Note that the Shapefile writer has a geometry parameter, but the GML writer does not.

Bookmark: Reader Feature Types
Libraries (reader FILEGDB_1)
    attributes: LibraryName text(30), LibraryAddress text(30), LibraryURL text(80), BookCount int, UserVisits int, Circulation int, OBJECTID objectid, LibraryID text(6)
    -> Libraries (writer ESRISHAPE_1)
Parks (reader FILEGDB_1)
    attributes: ParkName text(30), ParkAddress text(50), ParkURL text(100), OBJECTID objectid
    -> Parks (writer ESRISHAPE_1)
Note: Geodatabase
TransitStations (reader FILEGDB_1)
    attributes: StationName text(30), OBJECTID objectid
    -> TransitStations (writer ESRISHAPE_1)

Bookmark: Writer Feature Types
Libraries (writer ESRISHAPE_1)
    attributes: LibraryNam char(30), LibraryAdd char(30), LibraryURL char(80), BookCount long, UserVisits long, Circulatio long, OBJECTID long, LibraryID char(6)
Parks (writer ESRISHAPE_1)
    attributes: ParkName char(30), ParkAddres char(50), ParkURL char(100), OBJECTID long
Note: Shapefile / Has Geometry Type Setting
TransitStations (writer ESRISHAPE_1)
    attributes: StationNam char(30), OBJECTID long

Bookmark: Writer Feature Type
Note: GML / Has No Geometry Type Setting
Parks (writer GML_1)
    attributes: ParkName xml_char(30), ParkAddress xml_char(50), ParkURL xml_char(100), OBJECTID xml_int32
