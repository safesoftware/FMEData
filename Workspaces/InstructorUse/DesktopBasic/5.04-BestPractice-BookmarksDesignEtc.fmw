FME workspace 5.04-BestPractice-BookmarksDesignEtc.fmw

Parameters:
- SourceDataset_FMW = C:\Users\imark\Dropbox\Best Practice Analysis\deleteme.fmw   # FME Workspace file to be analysed
- DestDataset_HTML = C:\FMEOutput\WorkspaceReport.html   # HTML Files(*.html)|*.html HTML report file

Readers:
- FMW_1: FMW from $(SourceDataset_FMW)

Writers:
- HTML_1: HTML to $(DestDataset_HTML)

Note: Best Practice Training / Do not attempt to run the workspace, simply use it to demonstrate bookmark use. / Bookmarks for Design / Demonstrate the overall layout. Show how the entire workspace is composed of multiple sections, each of which has a specific task and each of which is defined by a bookmark. / Demonstrate collapsing bookmarks. / Bookmarks for Access / Demonstrate how to access areas through clicking the bookmarks in the Navigator window. Also demonstrate the Bookmark Navigator (note, it will need to be added to the toolbar first) / Bookmarks for Editing / Demonstrate how sections of bookmark can be rearranged by dragging them about. Note that connections might get crossed, but that's OK because we have hidden connections here (more on that later...)
Readers (reader FMW_1)
    attributes: workspace_id uint32, reader_id uint32, reader_name string, reader_keyword string, reader_type string, source_dataset string, reader_enabled logical, reader_generate_build_number uint32
    -> Junction_12
Note: Readers
Junction_12
    -> Junction_13
FileProperties (reader FMW_1)
    attributes: workspace_id uint32, file_path string, file_size uint64, creation_date datetime, modified_date datetime, last_run_date datetime
WorkspaceProperties (reader FMW_1)
    attributes: workspace_id uint32, workspace_name string, modified_build_number uint32, category string, usage string, history string, requirement string, requirements_flag string
    -> Junction_19
Note: Workspaces
Junction_19
    -> Junction_20
FeatureTypeUserAttributes (reader FMW_1)
    attributes: workspace_id uint32, feature_type_id uint32, user_attribute_name string, user_attribute_type string
    -> Junction_63
Note: Writers
Junction_63
Annotations (reader FMW_1)
    attributes: workspace_id uint32, annotation_id uint32, annotation string, annotation_type string
ReaderHistogram (reader FMW_1)
    attributes: workspace_id uint32, reader_type string, reader_count uint32
TransformerOutputPortAttributes (reader FMW_1)
    attributes: workspace_id uint32, transformer_output_port_id string, transformer_output_port_attribute_name string, transformer_output_port_attribute_constant_value string, transformer_output_port_attribute_enabled string
Breakpoints (reader FMW_1)
    attributes: workspace_id uint32, breakpoint_id uint32, breakpoint_name string, breakpoint_condition string, breakpoint_test_clause string, breakpoint_enabled logical
    -> Junction_6
Note: Breakpoints
Junction_6
    -> Junction_7
FeatureTypeFormatAttributes (reader FMW_1)
    attributes: workspace_id uint32, feature_type_id uint32, format_attribute_name string, format_attribute_type string
FeatureTypeParameters (reader FMW_1)
    attributes: workspace_id uint32, feature_type_id uint32, feature_type_parameter_name string, feature_type_parameter_value string
WriterParameters (reader FMW_1)
    attributes: workspace_id uint32, writer_id uint32, writer_parameter_name string, writer_parameter_value string
    -> Junction_52
Note: Writers
Junction_52
WriterHistogram (reader FMW_1)
    attributes: workspace_id uint32, writer_type string, writer_count uint32
TransformerParameters (reader FMW_1)
    attributes: workspace_id uint32, transformer_id uint32, transformer_parameter_name string, transformer_parameter_value string
    -> Junction_25
    -> Junction_42
Note: Transformers
Junction_25
Note: Performance
Junction_42
    -> Junction_43
Bookmarks (reader FMW_1)
    attributes: workspace_id uint32, bookmark_id uint32, bookmark_name string, bookmark_description string
TransformerHistogram (reader FMW_1)
    attributes: workspace_id uint32, transformer_type string, transformer_count uint32
WriterFeatureTypes (reader FMW_1)
    attributes: workspace_id uint32, writer_id uint32, feature_type_id uint32, writer_feature_type_qualifier string, writer_feature_type_name string, writer_feature_type_possible_geometries string, writer_feature_type_enabled logical
    -> WriterFeatureTypes_-__Junction_31
Note: Writers
WriterFeatureTypes_-__Junction_31: Junction
ReaderFeatureTypes (reader FMW_1)
    attributes: workspace_id uint32, reader_id uint32, feature_type_id uint32, reader_feature_type_qualifier string, reader_feature_type_name string, reader_feature_type_possible_geometries string, reader_feature_type_enabled logical
    -> Junction_14
Note: Readers
Junction_14
    -> Junction_15
PublishedParameters (reader FMW_1)
    attributes: workspace_id uint32, published_parameter_name string, published_parameter_type string, published_parameter_default_value string
    -> Junction_71
    -> Junction_73
Note: Readers
Junction_71
    -> Junction_70
Note: Writers
Junction_73
Transformers (reader FMW_1)
    attributes: workspace_id uint32, transformer_id uint32, transformer_name string, transformer_type string, current_transformer_version uint8, max_transformer_version uint8, transformer_enabled logical, transformer_last_edit_build_number uint32
    -> Junction_23
    -> Junction_39
    -> Junction_60
Note: Transformers
Junction_23
Note: Writers
Junction_60
Note: Performance
Junction_39
    -> Junction_40
TransformerOutputPorts (reader FMW_1)
    attributes: workspace_id uint32, transformer_id uint32, transformer_output_port_id string, transformer_output_port_name string
ReaderParameters (reader FMW_1)
    attributes: workspace_id uint32, reader_id uint32, reader_parameter_name string, reader_parameter_value string
    -> Junction_51
Note: Writers
Junction_51
Writers (reader FMW_1)
    attributes: workspace_id uint32, writer_id uint32, writer_name string, writer_keyword string, writer_type string, destination_dataset string, writer_enabled logical, writer_generate_build_number uint32
    -> Writers_-__Junction_30
Note: Writers
Writers_-__Junction_30: Junction
Statistics (reader FMW_1)
    attributes: workspace_id uint32, num_published_parameters uint32, num_annotations uint32, num_bookmarks uint32, num_breakpoints uint32, num_readers uint32, num_reader_feature_types uint32, num_writers uint32, num_writer_feature_types uint32, num_transformers uint32, num_custom_transformers uint32, num_out_of_date_transformers uint32
    -> Junction_3
    -> Junction_11
Note: Bookmarks
Junction_3
    -> Junction_4
Note: Annotations
Junction_11
    -> Junction_10

Bookmark: 5: Reader Analysis
Note: Readers
Junction_13
    -> NoFeaturesTester_12
Note: Zero Readers Report
Note: Has No Readers
Junction_47
    -> FeatureMerger_7 [REQUESTOR]
Note: Reader FTs
Junction_15
    -> FeatureMerger [SUPPLIER]
    -> Tester_12
Note: Readers with a count of feature types
Note: Readers with No Feature Types
FeatureMerger
    ATTR_ACCUM_MODE = Merge Supplier
    ATTR_CONFLICT_RES = Use Requestor
    CONNECT_Z_MODE = First Wins
    GEOM_TYPE = Build Polygons
    IGNORE_NULLS = No
    JOIN_KEYS = @Value(reader_id) @Value(reader_id) AUTO
    MERGE_COUNT_ATTR = NumFeatureTypes
    MERGE_TYPE = Attributes Only
    PROCESS_DUPS = Yes
    REJECT_NULL_MISSING_KEYS = No
    SUPPLIERS_FIRST = No
    MERGED -> Tester_4
    NOT_MERGED -> NoFeaturesTester_2
FeatureMerger_7
    ATTR_ACCUM_MODE = Merge Supplier
    ATTR_CONFLICT_RES = Use Requestor
    CONNECT_Z_MODE = First Wins
    GEOM_TYPE = Build Polygons
    IGNORE_NULLS = No
    JOIN_KEYS = 1 1 AUTO
    MERGE_TYPE = Attributes Only
    PROCESS_DUPS = Yes
    REJECT_NULL_MISSING_KEYS = No
    SUPPLIERS_FIRST = No
    MERGED -> Sorter_2
    UNREFERENCED -> Sorter_2
Sorter_2
    SORT_PARM = SubOrder NUMERIC ASCENDING
    SORTED -> HTMLLayouter_2
Note: Has Readers
HTMLLayouter_2
    DIV_STYLE = NONE
    LAYOUT = VERTICAL
    -> AttributeManager_15
AttributeManager_15
    ATTR_TABLE = SET_TO ReportOrder = 5
    -> Junction_17
Note: Output
Junction_17
    -> Junction_2

Bookmark: 5.0: Check for Zero Readers
NoFeaturesTester_12
    NoInput -> HTMLReportGenerator_34
    -> FeatureMerger [REQUESTOR]
    -> FeatureMerger_4 [SUPPLIER]
    -> Tester_11
    -> ParameterFetcher_2
HTMLReportGenerator_34
    CONTENT_LIST = HEADER HEADER
    PAGE_CONFIG = HEADER{{TEXT;Reader Analysis;HEADER;H3;ALIGNMENT;LEFT;COLOR;0,0,0;FME_CONTROLLER_QUERY_FILE;transformers\dependencies\html5\Header.fme}}HEADER{{TEXT;This workspace contains no readers.;HEADER;H5;ALIGNMENT;LEFT;COLOR;0,0,0;FME_CONTROLLER_QUERY_FILE;transformers\dependencies\html5\Header.fme}}
    -> Junction_46
Note: Output
Junction_46
    -> Junction_47

Bookmark: 5.1: Reader Generation Version
ParameterFetcher_2
    ATTR_LIST = FMEBuildNum {$(FME_BUILD_NUM)}
    -> StringLengthCalculator_2
StringLengthCalculator_2
    LENGTH_ATTR = GenBuildLength
    SRC_ATTR = reader_generate_build_number
    -> SubstringExtractor_3
SubstringExtractor_3
    END = FME_CONDITIONAL:DEFAULT_VALUE'1'BOOL_OP;OR;COMPOSITE_TEST;<Unused>;TEST @Value(GenBuildLength) < 5'0'FME_NUM_CONDITIONS2___
    RESULT_ATTR = MajorBuildID
    SRC_STRING = @Value(reader_generate_build_number)
    START = 0
    -> SubstringExtractor_4
SubstringExtractor_4
    END = 1
    RESULT_ATTR = CurrentMajorBuild
    SRC_STRING = @Value(FMEBuildNum)
    START = 0
    -> Tester_7
Tester_7
    BOOL_OP = OR
    TEST_CLAUSE = TEST @Value(MajorBuildID) < @Value(CurrentMajorBuild)
    PASSED -> NoFeaturesTester_4
NoFeaturesTester_4
    NoInput -> AttributeManager_35
    -> AttributeManager_13
Note: Check build number length to identify older build
AttributeManager_13
    ATTR_TABLE:
      SET_TO ReadBuildHTML = <strong>WARNING:</strong> The reader @Value(reader_name) (@Value(reader_keyword)) was created in a major version (@Value(MajorBuildID)xxx) less than the current release build (@Value(FMEBuildNum)).<br>

      SET_TO WarnMsg = 1
    -> Junction_29
    -> HTMLReportGenerator_17
Note: Summary
Junction_29
    -> Junction_8
HTMLReportGenerator_17
    CONTENT_LIST = HEADER HEADER LIST HEADER
    PAGE_CONFIG:
      HEADER{{TEXT;Reader Analysis;HEADER;H3;ALIGNMENT;LEFT;COLOR;0,0,0;FME_CONTROLLER_QUERY_FILE;transformers\dependencies\html5\Header.fme}}HEADER{{TEXT;Reader Generation Versions;HEADER;H4;ALIGNMENT;LEFT;COLOR;0,0,0;FME_CONTROLLER_QUERY_FILE;transformers\dependencies\html5\Header.fme}}LIST{{ATTR;ReadBuildHTML;STYLE;NONE;COLOR;255,170,0;BADGE;;FME_CONTROLLER_QUERY_FILE;transformers\dependencies\html5\List.fme}}HEADER{{TEXT;<strong>Recommendations:</strong> You may wish to check if there are functionality and performance gains to be made by replacing these reader(s) with one generated with the current FME version.
      ;HEADER;NO;ALIGNMENT;LEFT;COLOR;0,0,0;FME_CONTROLLER_QUERY_FILE;transformers\dependencies\html5\Header.fme}}
    -> AttributeManager_34
AttributeManager_35
    ATTR_TABLE = SET_TO ReadBuildHTML = <strong>PASS:</strong> All readers were generated with the same major version of FME (@Substring($(FME_BUILD_NUM),0,2)xxx) as the current release build ($(FME_BUILD_NUM)).
    -> HTMLReportGenerator_18
HTMLReportGenerator_18
    CONTENT_LIST = HEADER HEADER LIST
    PAGE_CONFIG = HEADER{{TEXT;Reader Analysis;HEADER;H3;ALIGNMENT;LEFT;COLOR;0,0,0;FME_CONTROLLER_QUERY_FILE;transformers\dependencies\html5\Header.fme}}HEADER{{TEXT;Reader Generation Versions;HEADER;H4;ALIGNMENT;LEFT;COLOR;0,0,0;FME_CONTROLLER_QUERY_FILE;transformers\dependencies\html5\Header.fme}}LIST{{ATTR;ReadBuildHTML;STYLE;NONE;COLOR;0,255,0;BADGE;;FME_CONTROLLER_QUERY_FILE;transformers\dependencies\html5\List.fme}}
    -> AttributeManager_34
Note: SubOrder:1
AttributeManager_34
    ATTR_TABLE = SET_TO SubOrder = 1
    -> FeatureMerger_7 [SUPPLIER]

Bookmark: 5.2: Disabled Readers and Reader Feature Types
Tester_11
    BOOL_OP = OR
    TEST_CLAUSE = TEST @Value(reader_enabled) = No
    PASSED -> NoFeaturesTester_9
NoFeaturesTester_9
    NoInput -> AttributeManager_50
    -> AttributeManager_49
AttributeManager_49
    ATTR_TABLE:
      SET_TO DisabledReaderText = <strong>WARNING:</strong> This workspace contains a reader - <i>@Value(reader_name) (@Value(reader_keyword))</i> - that is disabled.<br>
      SET_TO DisabledReaderRec = <strong>Recommendation:</strong> Although a disabled reader won't impact operation or performance, best practice suggests you consider removing it, to tidy the workspace before putting it into production.<br>
      SET_TO WarnMsg = 1
    -> StatisticsCalculator_8
    -> Junction_37
Note: Summary
Junction_37
    -> Junction_8
StatisticsCalculator_8
    COMPUTE_HISTOGRAM = NO
    COUNT_ATTR = NumDisabledReaders
    PREPEND_ATTR_NAME_CHOICE = For multiple results only
    STATS_ATTRS = reader_id
    COMPLETE -> HTMLReportGenerator_27
HTMLReportGenerator_27
    CONTENT_LIST = HEADER LIST HEADER
    PAGE_CONFIG = HEADER{{TEXT;Disabled Readers: @Value(NumDisabledReaders);HEADER;H4;ALIGNMENT;LEFT;COLOR;0,0,0;FME_CONTROLLER_QUERY_FILE;transformers\dependencies\html5\Header.fme}}LIST{{ATTR;DisabledReaderText;STYLE;NONE;COLOR;255,170,0;BADGE;;FME_CONTROLLER_QUERY_FILE;transformers\dependencies\html5\List.fme}}HEADER{{TEXT;@Value(DisabledReaderRec);HEADER;NO;ALIGNMENT;LEFT;COLOR;0,0,0;FME_CONTROLLER_QUERY_FILE;transformers\dependencies\html5\Header.fme}}
    -> AttributeManager_51
AttributeManager_50
    ATTR_TABLE = SET_TO DisabledReaderText = <strong>PASS:</strong> No reader in this workspace is disabled.
    -> HTMLReportGenerator_28
HTMLReportGenerator_28
    CONTENT_LIST = HEADER LIST
    PAGE_CONFIG = HEADER{{TEXT;Disabled Readers: 0;HEADER;H4;ALIGNMENT;LEFT;COLOR;0,0,0;FME_CONTROLLER_QUERY_FILE;transformers\dependencies\html5\Header.fme}}LIST{{ATTR;DisabledReaderText;STYLE;NONE;COLOR;0,255,0;BADGE;;FME_CONTROLLER_QUERY_FILE;transformers\dependencies\html5\List.fme}}
    -> AttributeManager_51
Note: SubOrder:2
AttributeManager_51
    ATTR_TABLE = SET_TO SubOrder = 2
    -> FeatureMerger_7 [SUPPLIER]
Tester_12
    BOOL_OP = OR
    TEST_CLAUSE = TEST @Value(reader_feature_type_enabled) = No
    PASSED -> NoFeaturesTester_10
NoFeaturesTester_10
    NoInput -> AttributeManager_52
    -> FeatureMerger_4 [REQUESTOR]
Note: So we can identify the reader a disabled FT belongs to
FeatureMerger_4
    ATTR_ACCUM_MODE = Merge Supplier
    ATTR_CONFLICT_RES = Use Requestor
    IGNORE_NULLS = No
    JOIN_KEYS = @Value(reader_id) @Value(reader_id) AUTO
    MERGE_TYPE = Attributes Only
    PROCESS_DUPS = No
    REJECT_NULL_MISSING_KEYS = No
    SUPPLIERS_FIRST = No
    MERGED -> AttributeManager_54
AttributeManager_54
    ATTR_TABLE:
      SET_TO DisabledRFTText = <strong>WARNING:</strong> This workspace contains a reader feature type - <i>@Value(reader_feature_type_name) (Writer: @Value(reader_name) (@Value(reader_keyword)))</i> - that is disabled.<br>
      SET_TO DisabledRFTRec = <strong>Recommendation:</strong> Although a disabled feature type won't impact operation or performance, best practice suggests you consider removing it, to tidy the workspace before putting it into production.<br>
      SET_TO WarnMsg = 1
    -> Junction_38
    -> StatisticsCalculator_9
Note: Summary
Junction_38
    -> Junction_8
StatisticsCalculator_9
    COMPUTE_HISTOGRAM = NO
    COUNT_ATTR = NumDisabledRFTs
    PREPEND_ATTR_NAME_CHOICE = For multiple results only
    STATS_ATTRS = feature_type_id
    COMPLETE -> HTMLReportGenerator_30
HTMLReportGenerator_30
    CONTENT_LIST = HEADER LIST HEADER
    PAGE_CONFIG = HEADER{{TEXT;Disabled Reader Feature Types: @Value(NumDisabledRFTs);HEADER;H4;ALIGNMENT;LEFT;COLOR;0,0,0;FME_CONTROLLER_QUERY_FILE;transformers\dependencies\html5\Header.fme}}LIST{{ATTR;DisabledRFTText;STYLE;NONE;COLOR;255,170,0;BADGE;;FME_CONTROLLER_QUERY_FILE;transformers\dependencies\html5\List.fme}}HEADER{{TEXT;@Value(DisabledRFTRec);HEADER;NO;ALIGNMENT;LEFT;COLOR;0,0,0;FME_CONTROLLER_QUERY_FILE;transformers\dependencies\html5\Header.fme}}
    -> AttributeManager_53
AttributeManager_52
    ATTR_TABLE = SET_TO DisabledReaderFTText = <strong>PASS:</strong>No reader feature types in this workspace are disabled.
    -> HTMLReportGenerator_29
HTMLReportGenerator_29
    CONTENT_LIST = HEADER LIST
    PAGE_CONFIG = HEADER{{TEXT;Disabled Reader Feature Types: 0;HEADER;H4;ALIGNMENT;LEFT;COLOR;0,0,0;FME_CONTROLLER_QUERY_FILE;transformers\dependencies\html5\Header.fme}}LIST{{ATTR;DisabledReaderFTText;STYLE;NONE;COLOR;0,255,0;BADGE;;FME_CONTROLLER_QUERY_FILE;transformers\dependencies\html5\List.fme}}
    -> AttributeManager_53
Note: SubOrder:2.5
AttributeManager_53
    ATTR_TABLE = SET_TO SubOrder = 2.5
    -> FeatureMerger_7 [SUPPLIER]

Bookmark: 2.1 Last edits not in current FME (Version, NOT build)
Junction_20
    -> ParameterFetcher
    -> Tester_6
ParameterFetcher
    ATTR_LIST = FMEBuildNum {$(FME_BUILD_NUM)}
    -> StringLengthCalculator
StringLengthCalculator
    LENGTH_ATTR = ModBuildLength
    SRC_ATTR = modified_build_number
    -> SubstringExtractor
Note: Check build number length to identify older build
SubstringExtractor
    END = FME_CONDITIONAL:DEFAULT_VALUE'1'BOOL_OP;OR;COMPOSITE_TEST;<Unused>;TEST @Value(ModBuildLength) < 5'0'FME_NUM_CONDITIONS2___
    RESULT_ATTR = MajorBuildID
    SRC_STRING = @Value(modified_build_number)
    START = 0
    -> SubstringExtractor_2
SubstringExtractor_2
    END = 1
    RESULT_ATTR = CurrentMajorBuild
    SRC_STRING = @Value(FMEBuildNum)
    START = 0
    -> TestFilter_2
Note: Test a) built in older FME / b) build in newer (beta) FME
TestFilter_2
    DEFAULT_VALUE = CurrentConstruction
    TEST_LIST = BOOL_OP,OR,COMPOSITE_TEST,<Unused>,TEST_CLAUSE,"TEST @Value(MajorBuildID) < @Value(CurrentMajorBuild)",OlderConstruction,BOOL_OP,OR,COMPOSITE_TEST,<Unused>,TEST_CLAUSE,"TEST @Value(MajorBuildID) > @Value(CurrentMajorBuild)",NewerConstruction
    OlderConstruction -> AttributeManager_27
    NewerConstruction -> AttributeManager_69
    CurrentConstruction -> AttributeManager_22
AttributeManager_27
    ATTR_TABLE:
      SET_TO MajorBuildText = <strong>WARNING:</strong>The major version of your workspace (@Value(MajorBuildID)xxx) is less than the current release build (@Value(FMEBuildNum)), indicating an older construction.
      SET_TO MajorBuildRec = <strong>Recommendation:</strong> Before deploying your workspace on the latest FME version you should be sure to thoroughly test the results it produces on that version.
      SET_TO WarnMsg = 1
    -> HTMLReportGenerator_14
    -> Junction_21
HTMLReportGenerator_14
    CONTENT_LIST = HEADER HEADER LIST HEADER
    PAGE_CONFIG = HEADER{{TEXT;Workspace Analysis;HEADER;H3;ALIGNMENT;LEFT;COLOR;0,0,0;FME_CONTROLLER_QUERY_FILE;transformers\dependencies\html5\Header.fme}}HEADER{{TEXT;Last Edited in Build: @Value(modified_build_number);HEADER;H4;ALIGNMENT;LEFT;COLOR;0,0,0;FME_CONTROLLER_QUERY_FILE;transformers\dependencies\html5\Header.fme}}LIST{{ATTR;MajorBuildText;STYLE;NONE;COLOR;255,170,0;BADGE;;FME_CONTROLLER_QUERY_FILE;transformers\dependencies\html5\List.fme}}HEADER{{TEXT;@Value(MajorBuildRec);HEADER;NO;ALIGNMENT;LEFT;COLOR;0,0,0;FME_CONTROLLER_QUERY_FILE;transformers\dependencies\html5\Header.fme}}
    -> AttributeManager_29
AttributeManager_69
    ATTR_TABLE:
      SET_TO MajorBuildText = <strong>ERROR:</strong>The major version of your workspace (@Value(MajorBuildID)xxx) is greater than the current release build (@Value(FMEBuildNum)) indicating use of a beta version.

      SET_TO MajorBuildRec = <strong>Recommendation:</strong> You are strongly recommended to not deploy a workspace for production when it is produced in a newer version of FME, particularly a beta build.
      SET_TO ErrorMsg = 1
    -> HTMLReportGenerator_38
    -> Junction_21
Note: Summary
Junction_21
    -> Junction_8
HTMLReportGenerator_38
    CONTENT_LIST = HEADER HEADER LIST HEADER
    PAGE_CONFIG = HEADER{{TEXT;Workspace Analysis;HEADER;H3;ALIGNMENT;LEFT;COLOR;0,0,0;FME_CONTROLLER_QUERY_FILE;transformers\dependencies\html5\Header.fme}}HEADER{{TEXT;Last Edited in Build: @Value(modified_build_number);HEADER;H4;ALIGNMENT;LEFT;COLOR;0,0,0;FME_CONTROLLER_QUERY_FILE;transformers\dependencies\html5\Header.fme}}LIST{{ATTR;MajorBuildText;STYLE;NONE;COLOR;255,0,0;BADGE;;FME_CONTROLLER_QUERY_FILE;transformers\dependencies\html5\List.fme}}HEADER{{TEXT;@Value(MajorBuildRec);HEADER;NO;ALIGNMENT;LEFT;COLOR;0,0,0;FME_CONTROLLER_QUERY_FILE;transformers\dependencies\html5\Header.fme}}
    -> AttributeManager_29
AttributeManager_22
    ATTR_TABLE = SET_TO MajorBuildText = <strong>PASS:</strong>The major version of your workspace (@Value(MajorBuildID)xxx) is the same as the current release build (@Value(FMEBuildNum)).
    -> HTMLReportGenerator_13
HTMLReportGenerator_13
    CONTENT_LIST = HEADER HEADER LIST
    PAGE_CONFIG = HEADER{{TEXT;Workspace Analysis;HEADER;H3;ALIGNMENT;LEFT;COLOR;0,0,0;FME_CONTROLLER_QUERY_FILE;transformers\dependencies\html5\Header.fme}}HEADER{{TEXT;Last Edited in Build: @Value(modified_build_number);HEADER;H4;ALIGNMENT;LEFT;COLOR;0,0,0;FME_CONTROLLER_QUERY_FILE;transformers\dependencies\html5\Header.fme}}LIST{{ATTR;MajorBuildText;STYLE;NONE;COLOR;0,255,0;BADGE;;FME_CONTROLLER_QUERY_FILE;transformers\dependencies\html5\List.fme}}
    -> AttributeManager_29
AttributeManager_29
    ATTR_TABLE = SET_TO SubOrder = 1
    -> Sorter_3

Bookmark: 2.2 Workspace Properties (Check Name/Category are set)
Tester_6
    BOOL_OP = AND
    TEST_CLAUSE:
      TEST @Value(category) ATTRIBUTE_HAS_VALUE ""
      TEST @Value(workspace_name) ATTRIBUTE_HAS_VALUE ""
    PASSED -> AttributeManager_28
    FAILED -> AttributeManager_31
AttributeManager_28
    ATTR_TABLE:
      SET_TO WkspPropertiesText = <strong>PASS:</strong>Both your workspace name and category properties are set. These are important pieces of metadata.<br>
        You should also be sure to set other workspace properties such as the description, history, and requirements fields, if they are not already.
    -> HTMLReportGenerator_15
HTMLReportGenerator_15
    CONTENT_LIST = HEADER LIST
    PAGE_CONFIG = HEADER{{TEXT;Workspace Name: <i>@Value(workspace_name)</i>. Workspace Category: <i>@Value(category)</i>;HEADER;H4;ALIGNMENT;LEFT;COLOR;0,0,0;FME_CONTROLLER_QUERY_FILE;transformers\dependencies\html5\Header.fme}}LIST{{ATTR;WkspPropertiesText;STYLE;NONE;COLOR;0,255,0;BADGE;;FME_CONTROLLER_QUERY_FILE;transformers\dependencies\html5\List.fme}}
    -> AttributeManager_30
AttributeManager_31
    ATTR_TABLE:
      SET_TO WkspPropertiesText = FME_CONDITIONAL:DEFAULT_VALUE'<strong>WARNING:</strong>The workspace name is not set in the workspace properties dialogs.'BOOL_OP;AND;COMPOSITE_TEST;<Unused>;TEST @Value(workspace_name) NOT_ATTRIBUTE_HAS_VALUE _FME_BLANK_STRING_;TEST @Value(category) NOT_ATTRIBUTE_HAS_VALUE _FME_BLANK_STRING_'<strong>WARNING:</strong>Neither the workspace name or workspace category are set in the workspace properties dialogs.'BOOL_OP;AND;COMPOSITE_TEST;<Unused>;TEST @Value(category) NOT_ATTRIBUTE_HAS_VALUE _FME_BLANK_STRING_'<strong>WARNING:</strong>The workspace category is not set in the workspace properties dialogs.'FME_NUM_CONDITIONS3___
      SET_TO WkspPropertiesRec = FME_CONDITIONAL:DEFAULT_VALUE'<strong>Recommendation:</strong>This is an important piece of metadata. It should be set for all workspaces, particularly those to be deployed on FME Server or FME Hub.
        'BOOL_OP;AND;COMPOSITE_TEST;<Unused>;TEST @Value(workspace_name) NOT_ATTRIBUTE_HAS_VALUE _FME_BLANK_STRING_;TEST @Value(category) NOT_ATTRIBUTE_HAS_VALUE _FME_BLANK_STRING_'<strong>Recommendation:</strong>These are important pieces of metadata. They should be set for all workspaces, particularly those to be deployed on FME Server or FME Hub.
        'BOOL_OP;AND;COMPOSITE_TEST;<Unused>;TEST @Value(category) NOT_ATTRIBUTE_HAS_VALUE _FME_BLANK_STRING_'<strong>Recommendation:</strong>This is an important piece of metadata. It should be set for all workspaces, particularly those to be deployed on FME Server or FME Hub.
        'FME_NUM_CONDITIONS3___
      SET_TO WarnMsg = 1
      SET_TO workspace_name = FME_CONDITIONAL:DEFAULT_VALUE'_FME_NO_OP_'BOOL_OP;OR;COMPOSITE_TEST;<Unused>;TEST @Value(workspace_name) NOT_ATTRIBUTE_HAS_VALUE _FME_BLANK_STRING_'None'FME_NUM_CONDITIONS2___
      SET_TO category = FME_CONDITIONAL:DEFAULT_VALUE'_FME_NO_OP_'BOOL_OP;OR;COMPOSITE_TEST;<Unused>;TEST @Value(category) NOT_ATTRIBUTE_HAS_VALUE _FME_BLANK_STRING_'None'FME_NUM_CONDITIONS2___
    -> HTMLReportGenerator_16
    -> Junction_22
HTMLReportGenerator_16
    CONTENT_LIST = HEADER LIST HEADER
    PAGE_CONFIG = HEADER{{TEXT;Workspace Name: <i>@Value(workspace_name)</i>. Workspace Category: <i>@Value(category)</i>.;HEADER;H4;ALIGNMENT;LEFT;COLOR;0,0,0;FME_CONTROLLER_QUERY_FILE;transformers\dependencies\html5\Header.fme}}LIST{{ATTR;WkspPropertiesText;STYLE;NONE;COLOR;255,170,0;BADGE;;FME_CONTROLLER_QUERY_FILE;transformers\dependencies\html5\List.fme}}HEADER{{TEXT;@Value(WkspPropertiesRec);HEADER;NO;ALIGNMENT;LEFT;COLOR;0,0,0;FME_CONTROLLER_QUERY_FILE;transformers\dependencies\html5\Header.fme}}
    -> AttributeManager_30
AttributeManager_30
    ATTR_TABLE = SET_TO SubOrder = 2
    -> Sorter_3
Note: Summary
Junction_22
    -> Junction_8

Bookmark: 2: Workspace Analysis
Sorter_3
    SORT_PARM = SubOrder NUMERIC ASCENDING
    SORTED -> HTMLLayouter_3
HTMLLayouter_3
    DIV_STYLE = NONE
    LAYOUT = VERTICAL
    -> AttributeManager_26
AttributeManager_26
    ATTR_TABLE = SET_TO ReportOrder = 2
    -> AttributeManager_26_OUTPUT
Note: Output
AttributeManager_26_OUTPUT: Junction
    -> Junction_2

Bookmark: 4: Breakpoint Analysis
Note: Breakpoints
Junction_7
    -> NoFeaturesTester
NoFeaturesTester
    NoInput -> AttributeManager_20
    -> StatisticsCalculator_3
Note: No Breakpoints
AttributeManager_20
    ATTR_TABLE = SET_TO BreakPointText = <strong>PASS:</strong> You have no breakpoints in your workspace
    -> HTMLReportGenerator_5
HTMLReportGenerator_5
    CONTENT_LIST = HEADER HEADER LIST
    PAGE_CONFIG = HEADER{{TEXT;Breakpoint Analysis;HEADER;H3;ALIGNMENT;LEFT;COLOR;0,0,0;FME_CONTROLLER_QUERY_FILE;transformers\dependencies\html5\Header.fme}}HEADER{{TEXT;Breakpoint Count: 0;HEADER;H4;ALIGNMENT;LEFT;COLOR;0,0,0;FME_CONTROLLER_QUERY_FILE;transformers\dependencies\html5\Header.fme}}LIST{{ATTR;BreakPointText;STYLE;NONE;COLOR;0,255,0;BADGE;;FME_CONTROLLER_QUERY_FILE;transformers\dependencies\html5\List.fme}}
    -> AttributeManager_7
StatisticsCalculator_3
    COMPUTE_HISTOGRAM = NO
    COUNT_ATTR = NumBreakpoints
    PREPEND_ATTR_NAME_CHOICE = For multiple results only
    STATS_ATTRS = breakpoint_id
    COMPLETE -> Tester_2
Tester_2
    BOOL_OP = OR
    TEST_CLAUSE = TEST @Value(breakpoint_enabled) = No
    PASSED -> AttributeManager_8
    FAILED -> AttributeManager_9
Note: Disabled Breakpoint
AttributeManager_8
    ATTR_TABLE:
      SET_TO HTMLBkptWarning = <strong>WARNING:</strong> This workspace contains a disabled breakpoint at: <i>@Value(breakpoint_name).</i><br>

      SET_TO ErrorMsg = 1
    -> Junction_9
    -> HTMLReportGenerator_6
Note: Enabled Breakpoint
AttributeManager_9
    ATTR_TABLE:
      SET_TO HTMLBkptError = <strong>ERROR:</strong> This workspace contains an active breakpoint at:<i> @Value(breakpoint_name).</i><br>

      SET_TO WarnMsg = 1
    -> Junction_9
    -> HTMLReportGenerator_6
Note: Summary
Junction_9
    -> Junction_8
HTMLReportGenerator_6
    CONTENT_LIST = HEADER HEADER LIST LIST HEADER
    PAGE_CONFIG = HEADER{{TEXT;Breakpoint Analysis;HEADER;H3;ALIGNMENT;LEFT;COLOR;0,0,0;FME_CONTROLLER_QUERY_FILE;transformers\dependencies\html5\Header.fme}}HEADER{{TEXT;Breakpoint Count: @Value(NumBreakpoints);HEADER;H4;ALIGNMENT;LEFT;COLOR;0,0,0;FME_CONTROLLER_QUERY_FILE;transformers\dependencies\html5\Header.fme}}LIST{{ATTR;HTMLBkptError;STYLE;NONE;COLOR;255,0,0;BADGE;;FME_CONTROLLER_QUERY_FILE;transformers\dependencies\html5\List.fme}}LIST{{ATTR;HTMLBkptWarning;STYLE;NONE;COLOR;255,170,0;BADGE;;FME_CONTROLLER_QUERY_FILE;transformers\dependencies\html5\List.fme}}HEADER{{TEXT;<strong>Recommendations:</strong> You may wish to remove these breakpoint(s). Breakpoints should be used solely for debugging and removed before putting a workspace into production.;HEADER;NO;ALIGNMENT;LEFT;COLOR;0,0,0;FME_CONTROLLER_QUERY_FILE;transformers\dependencies\html5\Header.fme}}
    -> AttributeManager_7
AttributeManager_7
    ATTR_TABLE = SET_TO ReportOrder = 4
    -> AttributeManager_7_OUTPUT
Note: Output
AttributeManager_7_OUTPUT: Junction
    -> Junction_2

Bookmark: 8: Performance Analysis
Note: Transformer Parameters
Junction_43
    -> FeatureMerger_5 [SUPPLIER]
Note: Transformers
Junction_40
    -> FeatureMerger_5 [REQUESTOR]
FeatureMerger_5
    ATTR_ACCUM_MODE = Merge Supplier
    ATTR_CONFLICT_RES = Use Requestor
    CONNECT_Z_MODE = First Wins
    GEOM_TYPE = Build Polygons
    IGNORE_NULLS = No
    JOIN_KEYS = @Value(transformer_id) @Value(transformer_id) AUTO
    LIST_NAME = TransParamList
    MERGE_TYPE = Attributes Only
    PROCESS_DUPS = Yes
    REJECT_NULL_MISSING_KEYS = No
    SUPPLIERS_FIRST = No
    MERGED -> AttributeFilter
    MERGED -> ListExploder_2
ListExploder_2
    ATTR_ACCUM_MODE = Merge Incoming List
    ATTR_CONFLICT_RES = Use Incoming List
    INDEX_ATTR = _element_index
    LIST_ATTR = TransParamList{}
    ELEMENTS -> Tester_13
    ELEMENTS -> Tester_14
Note: Summary
AttributeManager_60_OUTPUT: Junction
    -> Junction_8
Sorter_6
    SORT_PARM = SubOrder NUMERIC ASCENDING
    SORTED -> HTMLLayouter_6
HTMLLayouter_6
    DIV_STYLE = NONE
    LAYOUT = VERTICAL
    -> AttributeManager_57
Note: This merge ensures that the recommendation message appears because it is attached to all features
AttributeManager_57
    ATTR_TABLE = SET_TO ReportOrder = 8
    -> Junction_45
Note: Output
Junction_45
    -> Junction_2

Bookmark: 5.3: Dangling Readers
NoFeaturesTester_2
    NoInput -> AttributeManager_17
    -> StatisticsCalculator_6
StatisticsCalculator_6
    COMPUTE_HISTOGRAM = NO
    COUNT_ATTR = DanglingReaders
    PREPEND_ATTR_NAME_CHOICE = For multiple results only
    STATS_ATTRS = reader_id
    COMPLETE -> AttributeManager_16
Note: Readers without a Feature Type
AttributeManager_16
    ATTR_TABLE:
      SET_TO DanglingReaderText = <strong>ERROR:</strong> This workspace contains a "dangling reader", <i> @Value(reader_name) (@Value(reader_keyword)).</i><br>
      SET_TO ErrorMsg = 1
      SET_TO DanglingReaderRec = <strong>Recommendation:</strong> A dangling reader is one without feature types. These should be avoided for performance reasons.<br>
    -> HTMLReportGenerator_9
    -> Junction_16
Note: Summary
Junction_16
    -> Junction_8
HTMLReportGenerator_9
    CONTENT_LIST = HEADER LIST HEADER
    PAGE_CONFIG = HEADER{{TEXT;Dangling Readers: @Value(DanglingReaders);HEADER;H4;ALIGNMENT;LEFT;COLOR;0,0,0;FME_CONTROLLER_QUERY_FILE;transformers\dependencies\html5\Header.fme}}LIST{{ATTR;DanglingReaderText;STYLE;NONE;COLOR;255,0,0;BADGE;;FME_CONTROLLER_QUERY_FILE;transformers\dependencies\html5\List.fme}}HEADER{{TEXT;@Value(DanglingReaderRec);HEADER;NO;ALIGNMENT;LEFT;COLOR;0,0,0;FME_CONTROLLER_QUERY_FILE;transformers\dependencies\html5\Header.fme}}
    -> AttributeManager_25
AttributeManager_17
    ATTR_TABLE = SET_TO DanglingReaderText = <strong>PASS:</strong> This workspace contains zero "dangling readers", readers without an attached feature type.
    -> HTMLReportGenerator_10
HTMLReportGenerator_10
    CONTENT_LIST = HEADER LIST
    PAGE_CONFIG = HEADER{{TEXT;Dangling Readers: 0;HEADER;H4;ALIGNMENT;LEFT;COLOR;0,0,0;FME_CONTROLLER_QUERY_FILE;transformers\dependencies\html5\Header.fme}}LIST{{ATTR;DanglingReaderText;STYLE;NONE;COLOR;0,255,0;BADGE;;FME_CONTROLLER_QUERY_FILE;transformers\dependencies\html5\List.fme}}
    -> AttributeManager_25
Note: SubOrder:3
AttributeManager_25
    ATTR_TABLE = SET_TO SubOrder = 3
    -> FeatureMerger_7 [SUPPLIER]

Bookmark: 5.4: Excessive Feature Types
Tester_4
    BOOL_OP = OR
    TEST_CLAUSE = TEST @Value(NumFeatureTypes) >= 10
    PASSED -> NoFeaturesTester_3
NoFeaturesTester_3
    NoInput -> AttributeManager_23
    -> AttributeManager_21
AttributeManager_21
    ATTR_TABLE:
      SET_TO ExcessFTText = <strong>WARNING:</strong> This workspace contains a reader - <i>@Value(reader_name) (@Value(reader_keyword))</i> - with @Value(NumFeatureTypes) feature types.
      SET_TO WarnMsg = 1
      SET_TO ExcessFTRec = <strong>Recommendation:</strong> If a single reader has 10 or more feature types - especially connected to the same transformer - then it's possible a merge filter could be applied to tidy the workspace.<br>
    -> HTMLReportGenerator_12
    -> Junction_18
Note: Summary
Junction_18
    -> Junction_8
HTMLReportGenerator_12
    CONTENT_LIST = HEADER LIST HEADER
    PAGE_CONFIG = HEADER{{TEXT;Reader(s) with excessive feature types;HEADER;H4;ALIGNMENT;LEFT;COLOR;0,0,0;FME_CONTROLLER_QUERY_FILE;transformers\dependencies\html5\Header.fme}}LIST{{ATTR;ExcessFTText;STYLE;NONE;COLOR;255,170,0;BADGE;;FME_CONTROLLER_QUERY_FILE;transformers\dependencies\html5\List.fme}}HEADER{{TEXT;@Value(ExcessFTRec);HEADER;NO;ALIGNMENT;LEFT;COLOR;0,0,0;FME_CONTROLLER_QUERY_FILE;transformers\dependencies\html5\Header.fme}}
    -> AttributeManager_24
AttributeManager_23
    ATTR_TABLE = SET_TO NoExcessFTText = <strong>PASS:</strong>No reader in this workspace contains an excess of feature types.
    -> HTMLReportGenerator_11
HTMLReportGenerator_11
    CONTENT_LIST = HEADER LIST
    PAGE_CONFIG = HEADER{{TEXT;Reader(s) with excessive feature types;HEADER;H4;ALIGNMENT;LEFT;COLOR;0,0,0;FME_CONTROLLER_QUERY_FILE;transformers\dependencies\html5\Header.fme}}LIST{{ATTR;NoExcessFTText;STYLE;NONE;COLOR;0,255,0;BADGE;;FME_CONTROLLER_QUERY_FILE;transformers\dependencies\html5\List.fme}}
    -> AttributeManager_24
Note: SubOrder:4
AttributeManager_24
    ATTR_TABLE = SET_TO SubOrder = 4
    -> FeatureMerger_7 [SUPPLIER]

Bookmark: 5.5: Automatically Published Source Parameters
Note: PublishedParameters
Junction_70
    -> Tester_5
Tester_5
    BOOL_OP = OR
    TEST_CLAUSE = TEST @Value(published_parameter_name) BEGINS_WITH SourceDataset_
    PASSED -> AttributeManager_72
    PASSED -> NoFeaturesTester_14
AttributeManager_72
    ATTR_TABLE:
      SET_TO PubSourceParamText = <strong>WARNING:</strong> This workspace contains an automatically published source dataset parameter: <i>@Value(published_parameter_name)</i>.
      SET_TO PubSourceParamRec = <strong>Recommendation:</strong> Such parameters are published automatically by FME but are not always needed. If not required they should be deleted, so there is no confusion about what source datasets are allowed.
      SET_TO WarnMsg = 1
    -> HTMLReportGenerator_40
    -> Junction_72
Note: Summary
Junction_72
    -> Junction_8
HTMLReportGenerator_40
    CONTENT_LIST = HEADER LIST HEADER
    PAGE_CONFIG = HEADER{{TEXT;Automatic Source Dataset Published Parameters;HEADER;H4;ALIGNMENT;LEFT;COLOR;0,0,0;FME_CONTROLLER_QUERY_FILE;transformers\dependencies\html5\Header.fme}}LIST{{ATTR;PubSourceParamText;STYLE;NONE;COLOR;255,170,0;BADGE;;FME_CONTROLLER_QUERY_FILE;transformers\dependencies\html5\List.fme}}HEADER{{TEXT;@Value(PubSourceParamRec);HEADER;NO;ALIGNMENT;LEFT;COLOR;0,0,0;FME_CONTROLLER_QUERY_FILE;transformers\dependencies\html5\Header.fme}}
    -> AttributeManager_73
NoFeaturesTester_14
    NoInput -> AttributeManager_76
Note: Pass
AttributeManager_76
    ATTR_TABLE = SET_TO PubSourceParamText = <strong>PASS:</strong> This workspace contains no automatically published source dataset parameters.
    -> HTMLReportGenerator_42
HTMLReportGenerator_42
    CONTENT_LIST = HEADER LIST
    PAGE_CONFIG = HEADER{{TEXT;Automatic Source Dataset Published Parameters;HEADER;H4;ALIGNMENT;LEFT;COLOR;0,0,0;FME_CONTROLLER_QUERY_FILE;transformers\dependencies\html5\Header.fme}}LIST{{ATTR;PubSourceParamText;STYLE;NONE;COLOR;0,255,0;BADGE;;FME_CONTROLLER_QUERY_FILE;transformers\dependencies\html5\List.fme}}
    -> AttributeManager_73
AttributeManager_73
    ATTR_TABLE = SET_TO SubOrder = 5
    -> FeatureMerger_7 [SUPPLIER]

Bookmark: 8.1: Check for Aggressive or Extreme Parallel Processing
Tester_13
    BOOL_OP = COMPOSITE
    COMPOSITE_TEST = "1 AND (2 OR 3)"
    TEST_CLAUSE:
      TEST @Value(transformer_parameter_name) = FME_PROCESS_COUNTDISP
      TEST @Value(transformer_parameter_value) = Extreme
      TEST @Value(transformer_parameter_value) = Aggressive
    PASSED -> NoFeaturesTester_20
NoFeaturesTester_20
    NoInput -> AttributeManager_82
    -> AttributeManager_62
Note: Pass
AttributeManager_82
    ATTR_TABLE = SET_TO PPExAgWarn = <strong>PASS:</strong> No transformer has its Parallel Processing parameter set to Extreme or Aggressive.
    -> HTMLReportGenerator_48
HTMLReportGenerator_48
    CONTENT_LIST = HEADER HEADER LIST
    PAGE_CONFIG = HEADER{{TEXT;Performance Analysis;HEADER;H3;ALIGNMENT;LEFT;COLOR;0,0,0;FME_CONTROLLER_QUERY_FILE;transformers\dependencies\html5\Header.fme}}HEADER{{TEXT;Extreme or Aggressive Parallel Processing;HEADER;H4;ALIGNMENT;LEFT;COLOR;0,0,0;FME_CONTROLLER_QUERY_FILE;transformers\dependencies\html5\Header.fme}}LIST{{ATTR;PPExAgWarn;STYLE;NONE;COLOR;0,255,0;BADGE;;FME_CONTROLLER_QUERY_FILE;transformers\dependencies\html5\List.fme}}
    -> AttributeManager_63
AttributeManager_62
    ATTR_TABLE:
      SET_TO PPExAgWarn = <strong>WARNING:</strong> The transformer <i>@Value(transformer_name)</i> has its Parallel Processing parameter set to <i>@Value(transformer_parameter_value)</i><br>
      SET_TO PPExAgRec = <strong>Recommendations:</strong> Be sure this is appropriate. When the number of processes is greater than the number of cores, this can sometimes slow processing as much as improve it.
      SET_TO WarnMsg = 1
    -> AttributeManager_60_OUTPUT
    -> HTMLReportGenerator_33
HTMLReportGenerator_33
    CONTENT_LIST = HEADER HEADER LIST HEADER
    PAGE_CONFIG = HEADER{{TEXT;Performance Analysis;HEADER;H3;ALIGNMENT;LEFT;COLOR;0,0,0;FME_CONTROLLER_QUERY_FILE;transformers\dependencies\html5\Header.fme}}HEADER{{TEXT;Extreme or Aggressive Parallel Processing;HEADER;H4;ALIGNMENT;LEFT;COLOR;0,0,0;FME_CONTROLLER_QUERY_FILE;transformers\dependencies\html5\Header.fme}}LIST{{ATTR;PPExAgWarn;STYLE;NONE;COLOR;255,170,0;BADGE;;FME_CONTROLLER_QUERY_FILE;transformers\dependencies\html5\List.fme}}HEADER{{TEXT;@Value(PPExAgRec);HEADER;NO;ALIGNMENT;LEFT;COLOR;0,0,0;FME_CONTROLLER_QUERY_FILE;transformers\dependencies\html5\Header.fme}}
    -> AttributeManager_63
AttributeManager_63
    ATTR_TABLE = SET_TO SubOrder = 1
    -> Sorter_6

Bookmark: 8.2: Check for Multiple Parallel Processing Transformers
Tester_14
    BOOL_OP = AND
    TEST_CLAUSE:
      TEST @Value(transformer_parameter_name) = FME_PROCESS_COUNTDISP
      TEST @Value(transformer_parameter_value) != No Parallelism
    PASSED -> StatisticsCalculator_10
StatisticsCalculator_10
    COMPUTE_HISTOGRAM = NO
    COUNT_ATTR = NumParallelProcessing
    PREPEND_ATTR_NAME_CHOICE = For multiple results only
    STATS_ATTRS = transformer_id
    SUMMARY -> Tester_15
Tester_15
    BOOL_OP = OR
    TEST_CLAUSE = TEST @Value(NumParallelProcessing) > 1
    PASSED -> AttributeManager_60
    PASSED -> NoFeaturesTester_19
AttributeManager_60
    ATTR_TABLE:
      SET_TO MultiParallelMsg = <strong>WARNING:</strong> This workspace contains @Value(NumParallelProcessing) transformers set to parallel process data.<br>
      SET_TO MultiParallelRec = <strong>Recommendations:</strong> You may wish to limit a workspace to just a single parallel-processing transformer. Otherwise multiple transformers can launch multiple processes at the same time, leading to reduced performance.
      SET_TO WarnMsg = 1
    -> AttributeManager_60_OUTPUT
    -> HTMLReportGenerator_32
HTMLReportGenerator_32
    CONTENT_LIST = HEADER LIST HEADER
    PAGE_CONFIG = HEADER{{TEXT;Multiple Parallel Processing Transformers;HEADER;H4;ALIGNMENT;LEFT;COLOR;0,0,0;FME_CONTROLLER_QUERY_FILE;transformers\dependencies\html5\Header.fme}}LIST{{ATTR;MultiParallelMsg;STYLE;NONE;COLOR;255,170,0;BADGE;;FME_CONTROLLER_QUERY_FILE;transformers\dependencies\html5\List.fme}}HEADER{{TEXT;@Value(MultiParallelRec);HEADER;NO;ALIGNMENT;LEFT;COLOR;0,0,0;FME_CONTROLLER_QUERY_FILE;transformers\dependencies\html5\Header.fme}}
    -> AttributeManager_61
NoFeaturesTester_19
    NoInput -> AttributeManager_81
Note: Pass
AttributeManager_81
    ATTR_TABLE = SET_TO MultiParallelMsg = <strong>PASS:</strong> This workspace does not contain multiple transformers set to parallel process data.
    -> HTMLReportGenerator_47
HTMLReportGenerator_47
    CONTENT_LIST = HEADER LIST
    PAGE_CONFIG = HEADER{{TEXT;Multiple Parallel Processing Transformers;HEADER;H4;ALIGNMENT;LEFT;COLOR;0,0,0;FME_CONTROLLER_QUERY_FILE;transformers\dependencies\html5\Header.fme}}LIST{{ATTR;MultiParallelMsg;STYLE;NONE;COLOR;0,255,0;BADGE;;FME_CONTROLLER_QUERY_FILE;transformers\dependencies\html5\List.fme}}
    -> AttributeManager_61
AttributeManager_61
    ATTR_TABLE = SET_TO SubOrder = 2
    -> Sorter_6

Bookmark: 8.3: Check status of "X First" Parameters
Note: Transformers with an "X First" parameter
AttributeFilter
    ATTR_NAME = transformer_type
    ATTR_VALUES = Clipper,Displacer,FeatureMerger,NeighborFinder,PointOnAreaOverlayer,SpatialFilter,<EMPTY>,<MISSING>,<NULL>,<UNFILTERED>
    Clipper -> NoFeaturesTester_11
    Displacer -> NoFeaturesTester_11
    FeatureMerger -> NoFeaturesTester_11
    NeighborFinder -> NoFeaturesTester_11
    PointOnAreaOverlayer -> NoFeaturesTester_11
    SpatialFilter -> NoFeaturesTester_11
NoFeaturesTester_11
    NoInput -> Junction_41
    -> ListExploder
ListExploder
    ATTR_ACCUM_MODE = Merge Incoming List
    ATTR_CONFLICT_RES = Use Incoming List
    INDEX_ATTR = _element_index
    LIST_ATTR = TransParamList{}
    ELEMENTS -> TestFilter
TestFilter
    DEFAULT_VALUE = <UNFILTERED>
    TEST_LIST:
      BOOL_OP,AND,COMPOSITE_TEST,<Unused>,TEST_CLAUSE,"TEST @Value(transformer_type) = Clipper
      TEST @Value(transformer_parameter_name) = CLIP_TYPE
      TEST @Value(transformer_parameter_value) != Clippers First",ClipperXFirstNotSet,BOOL_OP,AND,COMPOSITE_TEST,<Unused>,TEST_CLAUSE,"TEST @Value(transformer_type) = Displacer
      TEST @Value(transformer_parameter_name) = BASE_TYPE
      TEST @Value(transformer_parameter_value) != Bases First",DisplacerXFirstNotSet,BOOL_OP,AND,COMPOSITE_TEST,<Unused>,TEST_CLAUSE,"TEST @Value(transformer_type) = FeatureMerger
      TEST @Value(transformer_parameter_name) = SUPPLIERS_FIRST
      TEST @Value(transformer_parameter_value) != Yes",FeatureMergerXFirstNotSet,BOOL_OP,AND,COMPOSITE_TEST,<Unused>,TEST_CLAUSE,"TEST @Value(transformer_type) = NeighborFinder
      TEST @Value(transformer_parameter_name) = CANDIDATES_FIRST
      TEST @Value(transformer_parameter_value) != Yes",NeighborFinderXFirstNotSet,BOOL_OP,AND,COMPOSITE_TEST,<Unused>,TEST_CLAUSE,"TEST @Value(transformer_type) = PointOnAreaOverlayer
      TEST @Value(transformer_parameter_name) = POLYS_FIRST
      TEST @Value(transformer_parameter_value) != YES",POAOXFirstNotSet,BOOL_OP,AND,COMPOSITE_TEST,<Unused>,TEST_CLAUSE,"TEST @Value(transformer_type) = SpatialFilter
      TEST @Value(transformer_parameter_name) = BASE_TYPE
      TEST @Value(transformer_parameter_value) != Filters First",SpatialFilterXFirstNotSet,BOOL_OP,AND,COMPOSITE_TEST,<Unused>,TEST_CLAUSE,"TEST @Value(transformer_type) = Clipper
      TEST @Value(transformer_parameter_name) = CLIP_TYPE
      TEST @Value(transformer_parameter_value) = Clippers First",ClipperXFirstSet,BOOL_OP,AND,COMPOSITE_TEST,<Unused>,TEST_CLAUSE,"TEST @Value(transformer_type) = Displacer
      TEST @Value(transformer_parameter_name) = BASE_TYPE
      TEST @Value(transformer_parameter_value) = Bases First",DisplacerXFirstSet,BOOL_OP,AND,COMPOSITE_TEST,<Unused>,TEST_CLAUSE,"TEST @Value(transformer_type) = FeatureMerger
      TEST @Value(transformer_parameter_name) = SUPPLIERS_FIRST
      TEST @Value(transformer_parameter_value) = Yes",FeatureMergerXFirstSet,BOOL_OP,AND,COMPOSITE_TEST,<Unused>,TEST_CLAUSE,"TEST @Value(transformer_type) = NeighborFinder
      TEST @Value(transformer_parameter_name) = CANDIDATES_FIRST
      TEST @Value(transformer_parameter_value) = Yes",NeighborFinderXFirstSet,BOOL_OP,AND,COMPOSITE_TEST,<Unused>,TEST_CLAUSE,"TEST @Value(transformer_type) = PointOnAreaOverlayer
      TEST @Value(transformer_parameter_name) = POLYS_FIRST
      TEST @Value(transformer_parameter_value) = YES",POAOXFirstSet,BOOL_OP,AND,COMPOSITE_TEST,<Unused>,TEST_CLAUSE,"TEST @Value(transformer_type) = SpatialFilter
      TEST @Value(transformer_parameter_name) = BASE_TYPE
      TEST @Value(transformer_parameter_value) = Filters First",SpatialFilterXFirstSet
    ClipperXFirstNotSet -> AttributeManager_56
    DisplacerXFirstNotSet -> AttributeManager_56
    FeatureMergerXFirstNotSet -> AttributeManager_56
    NeighborFinderXFirstNotSet -> AttributeManager_56
    POAOXFirstNotSet -> AttributeManager_56
    SpatialFilterXFirstNotSet -> AttributeManager_56
    ClipperXFirstSet -> AttributeManager_55
    DisplacerXFirstSet -> AttributeManager_55
    FeatureMergerXFirstSet -> AttributeManager_55
    NeighborFinderXFirstSet -> AttributeManager_55
    POAOXFirstSet -> AttributeManager_55
    SpatialFilterXFirstSet -> AttributeManager_55
AttributeManager_56
    ATTR_TABLE:
      SET_TO TransXFirstWarn = <strong>WARNING:</strong> The transformer <i>@Value(transformer_name)</i> has the parameter <i>@Value(transformer_parameter_name)</i> set to <i>@Value(transformer_parameter_value)</i><br>
      SET_TO TransXFirstRec = <strong>Recommendations:</strong> Setting an <strong>X First</strong> parameter to "Yes" (or a <strong>Type</strong> parameter to "X First") can greatly improve performance.
      SET_TO WarnMsg = 1
    -> Junction_44
    -> HTMLReportGenerator_31
    -> AttributeManager_59
Note: Summary!
Junction_44
    -> Junction_8
AttributeManager_59
    ATTR_TABLE:
      REMOVE TransXFirstWarn
      REMOVE WarnMsg
    -> FeatureMerger_6 [SUPPLIER]
Note: Need to update this. / If one transformer is not good, but others are, then this should not be an overall PASS
AttributeManager_55
    ATTR_TABLE = SET_TO TransXFirstContent = <strong>PASS:</strong> The transformer <i>@Value(transformer_name)</i> has the parameter <i>@Value(transformer_parameter_name)</i> set to <i>@Value(transformer_parameter_value)</i><br>
    -> FeatureMerger_6 [REQUESTOR]
FeatureMerger_6
    ATTR_ACCUM_MODE = Merge Supplier
    ATTR_CONFLICT_RES = Use Requestor
    IGNORE_NULLS = No
    JOIN_KEYS = 1 1 AUTO
    MERGE_TYPE = Attributes Only
    PROCESS_DUPS = No
    REJECT_NULL_MISSING_KEYS = No
    SUPPLIERS_FIRST = No
    MERGED -> HTMLReportGenerator_31
    NOT_MERGED -> HTMLReportGenerator_31
HTMLReportGenerator_31
    CONTENT_LIST = HEADER LIST LIST HEADER
    PAGE_CONFIG = HEADER{{TEXT;X First Parameters;HEADER;H4;ALIGNMENT;LEFT;COLOR;0,0,0;FME_CONTROLLER_QUERY_FILE;transformers\dependencies\html5\Header.fme}}LIST{{ATTR;TransXFirstContent;STYLE;NONE;COLOR;0,255,0;BADGE;;FME_CONTROLLER_QUERY_FILE;transformers\dependencies\html5\List.fme}}LIST{{ATTR;TransXFirstWarn;STYLE;NONE;COLOR;255,170,0;BADGE;;FME_CONTROLLER_QUERY_FILE;transformers\dependencies\html5\List.fme}}HEADER{{TEXT;@Value(TransXFirstRec);HEADER;NO;ALIGNMENT;LEFT;COLOR;0,0,0;FME_CONTROLLER_QUERY_FILE;transformers\dependencies\html5\Header.fme}}
    -> AttributeManager_58
AttributeManager_58
    ATTR_TABLE = SET_TO SubOrder = 3
    -> Sorter_6
Note: No transformers of that sort
Junction_41

Bookmark: 3.1: Bookmark Analysis
Junction_4
    -> AttributeManager_2
Note: Calculate Bookmark/Transformer Ratio
AttributeManager_2
    ATTR_TABLE = SET_TO BookmarkTransformerRatio = @Evaluate((@round((@Value(num_transformers)/@Value(num_bookmarks))*10))/10)
    -> Tester
Note: Check for no bookmarks
Tester
    BOOL_OP = OR
    TEST_CLAUSE = TEST @Value(num_bookmarks) = 0
    PASSED -> AttributeManager_18
    FAILED -> AttributeManager_3
AttributeManager_18
    ATTR_TABLE = SET_TO BookmarkText = <strong>ERROR:</strong> You have zero bookmarks. This indicates a lack of best practice!<br>
    -> HTMLReportGenerator_3
HTMLReportGenerator_3
    CONTENT_LIST = HEADER HEADER LIST HEADER
    PAGE_CONFIG = HEADER{{TEXT;Style Analysis;HEADER;H3;ALIGNMENT;LEFT;COLOR;0,0,0;FME_CONTROLLER_QUERY_FILE;transformers\dependencies\html5\Header.fme}}HEADER{{TEXT;Transformer to Bookmark Ratio: N/A;HEADER;H4;ALIGNMENT;LEFT;COLOR;0,0,0;FME_CONTROLLER_QUERY_FILE;transformers\dependencies\html5\Header.fme}}LIST{{ATTR;BookmarkText;STYLE;NONE;COLOR;255,0,0;BADGE;;FME_CONTROLLER_QUERY_FILE;transformers\dependencies\html5\List.fme}}HEADER{{TEXT;<strong>Recommendations:</strong> Use more bookmarks, one bookmark for approximately every 5-10 transformers.;HEADER;NO;ALIGNMENT;LEFT;COLOR;0,0,0;FME_CONTROLLER_QUERY_FILE;transformers\dependencies\html5\Header.fme}}
    -> AttributeManager_4
AttributeManager_4
    ATTR_TABLE = SET_TO ErrorMsg = 1
    -> AttributeManager_32
AttributeManager_3
    ATTR_TABLE:
      SET_TO HTMLGoodContent = FME_CONDITIONAL:DEFAULT_VALUE''BOOL_OP;AND;COMPOSITE_TEST;<Unused>;TEST @Value(BookmarkTransformerRatio) <= 10;TEST @Value(BookmarkTransformerRatio) >= 5'<strong>PASS:</strong> You have an appropriate number of bookmarks for your workspace'FME_NUM_CONDITIONS2___
      SET_TO HTMLBadContent = FME_CONDITIONAL:DEFAULT_VALUE'_FME_NO_OP_'BOOL_OP;OR;COMPOSITE_TEST;<Unused>;TEST @Value(BookmarkTransformerRatio) > 10'<strong>WARNING:</strong> This value is higher than desirable, indicating a lack of bookmarks.<br>
        <strong>Recommendation:</strong> Use more bookmarks, one bookmark for approximately every 5-10 transformers.'BOOL_OP;OR;COMPOSITE_TEST;<Unused>;TEST @Value(BookmarkTransformerRatio) < 5'<strong>WARNING:</strong> This value is lower than desirable, indicating an excess of bookmarks. <br>
        <strong>Recommendation:</strong> Use fewer, larger bookmarks.'FME_NUM_CONDITIONS3___
      SET_TO WarnMsg = FME_CONDITIONAL:DEFAULT_VALUE'0'BOOL_OP;OR;COMPOSITE_TEST;<Unused>;TEST @Value(BookmarkTransformerRatio) > 10;TEST @Value(BookmarkTransformerRatio) < 5'1'FME_NUM_CONDITIONS2___
      SET_TO HTMLBadRec = FME_CONDITIONAL:DEFAULT_VALUE'_FME_NO_OP_'BOOL_OP;OR;COMPOSITE_TEST;<Unused>;TEST @Value(BookmarkTransformerRatio) > 10'<strong>Recommendations:</strong> Use more bookmarks, one bookmark for approximately every 5-10 transformers.'BOOL_OP;OR;COMPOSITE_TEST;<Unused>;TEST @Value(BookmarkTransformerRatio) < 5'<strong>Recommendations:</strong> Use fewer, more targeted, bookmarks; one bookmark for approximately every 5-10 transformers.'FME_NUM_CONDITIONS3___
    -> HTMLReportGenerator_2
HTMLReportGenerator_2
    CONTENT_LIST = HEADER HEADER LIST LIST HEADER
    GROUP_BY = WarnMsg
    PAGE_CONFIG = HEADER{{TEXT;Style Analysis;HEADER;H3;ALIGNMENT;LEFT;COLOR;0,0,0;FME_CONTROLLER_QUERY_FILE;transformers\dependencies\html5\Header.fme}}HEADER{{TEXT;Transformer to Bookmark Ratio: @Value(BookmarkTransformerRatio) transformers for each bookmark;HEADER;H4;ALIGNMENT;LEFT;COLOR;0,0,0;FME_CONTROLLER_QUERY_FILE;transformers\dependencies\html5\Header.fme}}LIST{{ATTR;HTMLGoodContent;STYLE;NONE;COLOR;0,255,0;BADGE;;FME_CONTROLLER_QUERY_FILE;transformers\dependencies\html5\Header.fme}}LIST{{ATTR;HTMLBadContent;STYLE;NONE;COLOR;255,170,0;BADGE;;FME_CONTROLLER_QUERY_FILE;transformers\dependencies\html5\List.fme}}HEADER{{TEXT;@Value(HTMLBadRec);HEADER;NO;ALIGNMENT;LEFT;COLOR;0,0,0;FME_CONTROLLER_QUERY_FILE;transformers\dependencies\html5\Header.fme}}
    -> AttributeManager_32
AttributeManager_32
    ATTR_TABLE = SET_TO SubOrder = 1
    -> Sorter_4
    -> Junction_27

Bookmark: 3: Style Analysis
Note: Summary
Junction_27
    -> Junction_8
Sorter_4
    SORT_PARM = SubOrder NUMERIC ASCENDING
    SORTED -> HTMLLayouter_4
HTMLLayouter_4
    DIV_STYLE = NONE
    LAYOUT = VERTICAL
    -> AttributeManager_6
AttributeManager_6
    ATTR_TABLE = SET_TO ReportOrder = 3
    -> HTMLReportGenerator_2_OUTPUT_-__Junction_2
Note: Output
HTMLReportGenerator_2_OUTPUT_-__Junction_2: Junction
    -> Junction_2
Note: Summary
Junction_28
    -> Junction_8

Bookmark: 3.2: Annotation Analysis
Junction_10
    -> AttributeManager_10
Note: Calculate Annotation/Transformer Ratio
AttributeManager_10
    ATTR_TABLE = SET_TO AnnotationTransformerRatio = @Evaluate((@round((@Value(num_transformers)/@Value(num_annotations))*10))/10)
    -> Tester_3
Note: Check for no annotations
Tester_3
    BOOL_OP = OR
    TEST_CLAUSE = TEST @Value(num_annotations) = 0
    PASSED -> AttributeManager_19
    FAILED -> AttributeManager_11
AttributeManager_19
    ATTR_TABLE = SET_TO AnnotationText = <strong>ERROR:</strong> You have zero annotations. This indicates a lack of best practice!<br>
    -> HTMLReportGenerator_8
HTMLReportGenerator_8
    CONTENT_LIST = HEADER LIST HEADER
    PAGE_CONFIG = HEADER{{TEXT;Transformer to Annotation Ratio: N/A;HEADER;H4;ALIGNMENT;LEFT;COLOR;0,0,0;FME_CONTROLLER_QUERY_FILE;transformers\dependencies\html5\Header.fme}}LIST{{ATTR;AnnotationText;STYLE;NONE;COLOR;255,0,0;BADGE;;FME_CONTROLLER_QUERY_FILE;transformers\dependencies\html5\List.fme}}HEADER{{TEXT;<strong>Recommendation:</strong> Use more annotations, one annotation for approximately every 3-5 transformers.;HEADER;NO;ALIGNMENT;LEFT;COLOR;0,0,0;FME_CONTROLLER_QUERY_FILE;transformers\dependencies\html5\Header.fme}}
    -> AttributeManager_12
AttributeManager_12
    ATTR_TABLE = SET_TO ErrorMsg = 1
    -> AttributeManager_33
AttributeManager_11
    ATTR_TABLE:
      SET_TO HTMLGoodContent = FME_CONDITIONAL:DEFAULT_VALUE''BOOL_OP;AND;COMPOSITE_TEST;<Unused>;TEST @Value(AnnotationTransformerRatio) <= 5;TEST @Value(AnnotationTransformerRatio) >= 3'<strong>GOOD:</strong> You have an appropriate number of annotations for your workspace'FME_NUM_CONDITIONS2___
      SET_TO HTMLBadContent = FME_CONDITIONAL:DEFAULT_VALUE'_FME_NO_OP_'BOOL_OP;OR;COMPOSITE_TEST;<Unused>;TEST @Value(AnnotationTransformerRatio) > 5'<strong>WARNING:</strong> This value is higher than desirable, indicating a lack of annotation.<br>
        'BOOL_OP;OR;COMPOSITE_TEST;<Unused>;TEST @Value(AnnotationTransformerRatio) < 3'<strong>WARNING:</strong> This value is lower than desirable, indicating an excess of annotations.<br>
        'FME_NUM_CONDITIONS3___
      SET_TO WarnMsg = FME_CONDITIONAL:DEFAULT_VALUE'0'BOOL_OP;OR;COMPOSITE_TEST;<Unused>;TEST @Value(AnnotationTransformerRatio) > 5;TEST @Value(AnnotationTransformerRatio) < 3'1'FME_NUM_CONDITIONS2___
      SET_TO HTMLRecommendation = FME_CONDITIONAL:DEFAULT_VALUE'_FME_NO_OP_'BOOL_OP;OR;COMPOSITE_TEST;<Unused>;TEST @Value(AnnotationTransformerRatio) > 5'<strong>Recommendations:</strong> Use more annotations, one annotation for approximately every 3-5 transformers.'BOOL_OP;OR;COMPOSITE_TEST;<Unused>;TEST @Value(AnnotationTransformerRatio) < 3'<strong>Recommendation:</strong> It's not necessary to add annotations to every transformer. Use fewer, more targeted annotations.'FME_NUM_CONDITIONS3___
    -> HTMLReportGenerator_7
HTMLReportGenerator_7
    CONTENT_LIST = HEADER LIST LIST HEADER
    GROUP_BY = WarnMsg
    PAGE_CONFIG = HEADER{{TEXT;Transformer to Annotation Ratio: @Value(AnnotationTransformerRatio) transformers for each annotation;HEADER;H4;ALIGNMENT;LEFT;COLOR;0,0,0;FME_CONTROLLER_QUERY_FILE;transformers\dependencies\html5\Header.fme}}LIST{{ATTR;HTMLGoodContent;STYLE;NONE;COLOR;0,255,0;BADGE;;FME_CONTROLLER_QUERY_FILE;transformers\dependencies\html5\Header.fme}}LIST{{ATTR;HTMLBadContent;STYLE;NONE;COLOR;255,170,0;BADGE;;FME_CONTROLLER_QUERY_FILE;transformers\dependencies\html5\List.fme}}HEADER{{TEXT;@Value(HTMLRecommendation);HEADER;NO;ALIGNMENT;LEFT;COLOR;0,0,0;FME_CONTROLLER_QUERY_FILE;transformers\dependencies\html5\Header.fme}}
    -> AttributeManager_33
AttributeManager_33
    ATTR_TABLE = SET_TO SubOrder = 2
    -> Sorter_4
    -> Junction_28

Bookmark: 1: Report Header
Creator
    GEOMTYPE = Geometry Object
    NUM = 1
    CREATED -> HTMLReportGenerator
HTMLReportGenerator
    CONTENT_LIST = HEADER HEADER HEADER HEADER HEADER
    PAGE_CONFIG = HEADER{{TEXT;FME Workspace;HEADER;H1;ALIGNMENT;LEFT;COLOR;0,0,0;FME_CONTROLLER_QUERY_FILE;transformers\dependencies\html5\Header.fme}}HEADER{{TEXT; Best Practice Report;HEADER;H3;ALIGNMENT;LEFT;COLOR;0,0,0;FME_CONTROLLER_QUERY_FILE;transformers\dependencies\html5\Header.fme}}HEADER{{TEXT;This report examines best practices for a workspaces that is about to be put into production.;HEADER;H5;ALIGNMENT;LEFT;COLOR;0,0,0;FME_CONTROLLER_QUERY_FILE;transformers\dependencies\html5\Header.fme}}HEADER{{TEXT;It is assumed that the version of FME being used to generate this report ($(FME_BUILD_NUM)) is the newest release version available. If not, please contact the administrator of this system.;HEADER;H5;ALIGNMENT;LEFT;COLOR;0,0,0;FME_CONTROLLER_QUERY_FILE;transformers\dependencies\html5\Header.fme}}HEADER{{TEXT;Note that this report does not comment upon the suitability of the workspace to produce the desired result, merely the practices by which it has been constructed.;HEADER;H5;ALIGNMENT;LEFT;COLOR;0,0,0;FME_CONTROLLER_QUERY_FILE;transformers\dependencies\html5\Header.fme}}
    -> AttributeManager
AttributeManager
    ATTR_TABLE = SET_TO ReportOrder = 1
    -> Junction
Note: Sorter
Junction
    -> Junction_2

Bookmark: 11: Writer Analysis
Note: Writers
Junction_30
    -> NoFeaturesTester_13
    -> Junction_65
Note: Zero Writers
Junction_48
    -> FeatureMerger_8 [REQUESTOR]
Note: Writer FTs
Junction_31
    -> FeatureMerger_2 [SUPPLIER]
    -> Tester_10
    -> Junction_64
    -> StringSearcher
Note: Local Output
Junction_54
    -> FeatureMerger_8 [SUPPLIER]
FeatureMerger_8
    ATTR_ACCUM_MODE = Merge Supplier
    ATTR_CONFLICT_RES = Use Requestor
    CONNECT_Z_MODE = First Wins
    GEOM_TYPE = Build Polygons
    IGNORE_NULLS = No
    JOIN_KEYS = a a AUTO
    MERGE_TYPE = Attributes Only
    PROCESS_DUPS = Yes
    REJECT_NULL_MISSING_KEYS = No
    SUPPLIERS_FIRST = No
    MERGED -> Sorter_5
    UNREFERENCED -> Sorter_5
Note: Has No Writers
Sorter_5
    SORT_PARM = SubOrder NUMERIC ASCENDING
    SORTED -> HTMLLayouter_5
Note: Has Writers
HTMLLayouter_5
    DIV_STYLE = NONE
    LAYOUT = VERTICAL
    -> AttributeManager_36
AttributeManager_36
    ATTR_TABLE = SET_TO ReportOrder = 6
    -> Junction_33
Note: Output
Junction_33
    -> Junction_2

Bookmark: 6.0: Check for Zero Writers
NoFeaturesTester_13
    NoInput -> HTMLReportGenerator_35
    -> ParameterFetcher_3
    -> FeatureMerger_2 [REQUESTOR]
    -> FeatureMerger_3 [SUPPLIER]
    -> Tester_8
HTMLReportGenerator_35
    CONTENT_LIST = HEADER HEADER
    PAGE_CONFIG = HEADER{{TEXT;Writer Analysis;HEADER;H3;ALIGNMENT;LEFT;COLOR;0,0,0;FME_CONTROLLER_QUERY_FILE;transformers\dependencies\html5\Header.fme}}HEADER{{TEXT;This workspace contains no writers.;HEADER;H5;ALIGNMENT;LEFT;COLOR;0,0,0;FME_CONTROLLER_QUERY_FILE;transformers\dependencies\html5\Header.fme}}
    -> HTMLReportGenerator_35_OUTPUT
Note: Output
HTMLReportGenerator_35_OUTPUT: Junction
    -> Junction_48

Bookmark: 6.1: Writer Generation Version
ParameterFetcher_3
    ATTR_LIST = FMEBuildNum {$(FME_BUILD_NUM)}
    -> StringLengthCalculator_3
StringLengthCalculator_3
    LENGTH_ATTR = GenBuildLength
    SRC_ATTR = writer_generate_build_number
    -> SubstringExtractor_5
SubstringExtractor_5
    END = FME_CONDITIONAL:DEFAULT_VALUE'1'BOOL_OP;OR;COMPOSITE_TEST;<Unused>;TEST @Value(GenBuildLength) < 5'0'FME_NUM_CONDITIONS2___
    RESULT_ATTR = MajorBuildID
    SRC_STRING = @Value(writer_generate_build_number)
    START = 0
    -> SubstringExtractor_6
SubstringExtractor_6
    END = 1
    RESULT_ATTR = CurrentMajorBuild
    SRC_STRING = @Value(FMEBuildNum)
    START = 0
    -> Tester_9
Tester_9
    BOOL_OP = OR
    TEST_CLAUSE = TEST @Value(MajorBuildID) < @Value(CurrentMajorBuild)
    PASSED -> NoFeaturesTester_7
NoFeaturesTester_7
    NoInput -> AttributeManager_45
    -> AttributeManager_43
Note: Check build number length to identify older build
AttributeManager_43
    ATTR_TABLE:
      SET_TO ReadBuildHTML = <strong>WARNING:</strong>The writer @Value(writer_name) (@Value(writer_keyword)) was created in a major version (@Value(MajorBuildID)xxx) less than the current release build (@Value(FMEBuildNum)).<br>

      SET_TO WarnMsg = 1
    -> Junction_35
    -> HTMLReportGenerator_23
Note: Summary
Junction_35
    -> Junction_8
HTMLReportGenerator_23
    CONTENT_LIST = HEADER HEADER LIST HEADER
    PAGE_CONFIG:
      HEADER{{TEXT;Writer Analysis;HEADER;H3;ALIGNMENT;LEFT;COLOR;0,0,0;FME_CONTROLLER_QUERY_FILE;transformers\dependencies\html5\Header.fme}}HEADER{{TEXT;Writer Generation Versions;HEADER;H4;ALIGNMENT;LEFT;COLOR;0,0,0;FME_CONTROLLER_QUERY_FILE;transformers\dependencies\html5\Header.fme}}LIST{{ATTR;ReadBuildHTML;STYLE;NONE;COLOR;255,170,0;BADGE;;FME_CONTROLLER_QUERY_FILE;transformers\dependencies\html5\List.fme}}HEADER{{TEXT;<strong>Recommendations:</strong> You may wish to check if there are functionality and performance gains to be made by replacing these writer(s) with one generated with the current FME version.
      ;HEADER;NO;ALIGNMENT;LEFT;COLOR;0,0,0;FME_CONTROLLER_QUERY_FILE;transformers\dependencies\html5\Header.fme}}
    -> AttributeManager_44
AttributeManager_45
    ATTR_TABLE = SET_TO ReadBuildHTML = <strong>PASS:</strong>All writers were generated with the same major version of FME (@Substring($(FME_BUILD_NUM),0,2)xxx) as the current release build ($(FME_BUILD_NUM)).
    -> HTMLReportGenerator_24
HTMLReportGenerator_24
    CONTENT_LIST = HEADER HEADER LIST
    PAGE_CONFIG = HEADER{{TEXT;Writer Analysis;HEADER;H3;ALIGNMENT;LEFT;COLOR;0,0,0;FME_CONTROLLER_QUERY_FILE;transformers\dependencies\html5\Header.fme}}HEADER{{TEXT;Writer Generation Versions;HEADER;H4;ALIGNMENT;LEFT;COLOR;0,0,0;FME_CONTROLLER_QUERY_FILE;transformers\dependencies\html5\Header.fme}}LIST{{ATTR;ReadBuildHTML;STYLE;NONE;COLOR;0,255,0;BADGE;;FME_CONTROLLER_QUERY_FILE;transformers\dependencies\html5\List.fme}}
    -> AttributeManager_44
Note: SubOrder:1
AttributeManager_44
    ATTR_TABLE = SET_TO SubOrder = 1
    -> Junction_55
Note: Local Output
Junction_55
    -> Junction_54

Bookmark: 6.2: Disabled Writers and Writer Feature Types
Tester_8
    BOOL_OP = OR
    TEST_CLAUSE = TEST @Value(writer_enabled) = No
    PASSED -> NoFeaturesTester_6
NoFeaturesTester_6
    NoInput -> AttributeManager_40
    -> AttributeManager_39
AttributeManager_39
    ATTR_TABLE:
      SET_TO DisabledWriterText = <strong>WARNING:</strong> This workspace contains a writer - <i>@Value(writer_name) (@Value(writer_keyword))</i> - that is disabled.<br>
      SET_TO WarnMsg = 1
      SET_TO DisabledWriterRec = <strong>Recommendation:</strong> Although a disabled writer won't impact operation or performance, best practice suggests you consider removing it, to tidy the workspace before putting it into production.<br>
    -> StatisticsCalculator_5
    -> Junction_34
Note: Summary
Junction_34
    -> Junction_8
StatisticsCalculator_5
    COMPUTE_HISTOGRAM = NO
    COUNT_ATTR = NumDisabledWriters
    PREPEND_ATTR_NAME_CHOICE = For multiple results only
    STATS_ATTRS = writer_id
    COMPLETE -> HTMLReportGenerator_21
HTMLReportGenerator_21
    CONTENT_LIST = HEADER LIST HEADER
    PAGE_CONFIG = HEADER{{TEXT;Disabled Writers: @Value(NumDisabledWriters);HEADER;H4;ALIGNMENT;LEFT;COLOR;0,0,0;FME_CONTROLLER_QUERY_FILE;transformers\dependencies\html5\Header.fme}}LIST{{ATTR;DisabledWriterText;STYLE;NONE;COLOR;255,170,0;BADGE;;FME_CONTROLLER_QUERY_FILE;transformers\dependencies\html5\List.fme}}HEADER{{TEXT;@Value(DisabledWriterRec);HEADER;NO;ALIGNMENT;LEFT;COLOR;0,0,0;FME_CONTROLLER_QUERY_FILE;transformers\dependencies\html5\Header.fme}}
    -> AttributeManager_41
AttributeManager_40
    ATTR_TABLE = SET_TO DisabledWriterText = <strong>PASS:</strong> No writer in this workspace is disabled.
    -> HTMLReportGenerator_22
HTMLReportGenerator_22
    CONTENT_LIST = HEADER LIST
    PAGE_CONFIG = HEADER{{TEXT;Disabled Writers: 0;HEADER;H4;ALIGNMENT;LEFT;COLOR;0,0,0;FME_CONTROLLER_QUERY_FILE;transformers\dependencies\html5\Header.fme}}LIST{{ATTR;DisabledWriterText;STYLE;NONE;COLOR;0,255,0;BADGE;;FME_CONTROLLER_QUERY_FILE;transformers\dependencies\html5\List.fme}}
    -> AttributeManager_41
Note: SubOrder:2
AttributeManager_41
    ATTR_TABLE = SET_TO SubOrder = 2
    -> Junction_56
Note: Local Output
Junction_56
    -> Junction_54
Tester_10
    BOOL_OP = OR
    TEST_CLAUSE = TEST @Value(writer_feature_type_enabled) = No
    PASSED -> NoFeaturesTester_8
NoFeaturesTester_8
    NoInput -> AttributeManager_46
    -> FeatureMerger_3 [REQUESTOR]
Note: So we can identify the writer a disabled FT belongs to
FeatureMerger_3
    ATTR_ACCUM_MODE = Merge Supplier
    ATTR_CONFLICT_RES = Use Requestor
    IGNORE_NULLS = No
    JOIN_KEYS = @Value(writer_id) @Value(writer_id) AUTO
    MERGE_TYPE = Attributes Only
    PROCESS_DUPS = No
    REJECT_NULL_MISSING_KEYS = No
    SUPPLIERS_FIRST = No
    MERGED -> AttributeManager_48
AttributeManager_48
    ATTR_TABLE:
      SET_TO DisabledWFTText = <strong>WARNING:</strong> This workspace contains a writer feature type - <i>@Value(writer_feature_type_name) (Writer: @Value(writer_name) (@Value(writer_keyword)))</i> - that is disabled.<br>
      SET_TO WarnMsg = 1
      SET_TO DisabledWFTRec = <strong>Recommendation:</strong> Although a disabled feature type won't impact operation or performance, best practice suggests you consider removing it, to tidy the workspace before putting it into production.<br>
    -> Junction_36
    -> StatisticsCalculator_7
Note: Summary
Junction_36
    -> Junction_8
StatisticsCalculator_7
    COMPUTE_HISTOGRAM = NO
    COUNT_ATTR = NumDisabledWFTs
    PREPEND_ATTR_NAME_CHOICE = For multiple results only
    STATS_ATTRS = feature_type_id
    COMPLETE -> HTMLReportGenerator_26
HTMLReportGenerator_26
    CONTENT_LIST = HEADER LIST HEADER
    PAGE_CONFIG = HEADER{{TEXT;Disabled Writer Feature Types: @Value(NumDisabledWFTs);HEADER;H4;ALIGNMENT;LEFT;COLOR;0,0,0;FME_CONTROLLER_QUERY_FILE;transformers\dependencies\html5\Header.fme}}LIST{{ATTR;DisabledWFTText;STYLE;NONE;COLOR;255,170,0;BADGE;;FME_CONTROLLER_QUERY_FILE;transformers\dependencies\html5\List.fme}}HEADER{{TEXT;@Value(DisabledWFTRec);HEADER;NO;ALIGNMENT;LEFT;COLOR;0,0,0;FME_CONTROLLER_QUERY_FILE;transformers\dependencies\html5\Header.fme}}
    -> AttributeManager_47
AttributeManager_46
    ATTR_TABLE = SET_TO DisabledWriterFTText = <strong>PASS:</strong>No writer feature types in this workspace are disabled.
    -> HTMLReportGenerator_25
HTMLReportGenerator_25
    CONTENT_LIST = HEADER LIST
    PAGE_CONFIG = HEADER{{TEXT;Disabled Writer Feature Types: 0;HEADER;H4;ALIGNMENT;LEFT;COLOR;0,0,0;FME_CONTROLLER_QUERY_FILE;transformers\dependencies\html5\Header.fme}}LIST{{ATTR;DisabledWriterFTText;STYLE;NONE;COLOR;0,255,0;BADGE;;FME_CONTROLLER_QUERY_FILE;transformers\dependencies\html5\List.fme}}
    -> AttributeManager_47
Note: SubOrder:2.5
AttributeManager_47
    ATTR_TABLE = SET_TO SubOrder = 2.5
    -> Junction_57
Note: Local Output
Junction_57
    -> Junction_54

Bookmark: 6.5: Check Attribute Names that are a Mix of Cases. Not to blow my own trumpet, but I think this bit is pretty good!
Note: Writers
Junction_65
    -> FeatureMerger_11 [SUPPLIER]
Note: Writer FTs
Junction_64
    -> FeatureMerger_10 [SUPPLIER]
Note: FeatureTypeUserAttributes
Junction_62
    -> FeatureMerger_10 [REQUESTOR]
Note: Keep only writer FT attributes
FeatureMerger_10
    ATTR_ACCUM_MODE = Merge Supplier
    ATTR_CONFLICT_RES = Use Requestor
    IGNORE_NULLS = No
    JOIN_KEYS = @Value(feature_type_id) @Value(feature_type_id) AUTO
    MERGE_TYPE = Attributes Only
    PROCESS_DUPS = No
    REJECT_NULL_MISSING_KEYS = No
    SUPPLIERS_FIRST = No
    MERGED -> AttributeManager_68
Note: Conditional Case Mapping / UPPERCASE / 1 / lowercase / 2 / Full Title Case / 4 / Title case / 8 / Creates a "binary" value
AttributeManager_68
    ATTR_TABLE = SET_TO CaseCount = FME_CONDITIONAL:DEFAULT_VALUE'8'BOOL_OP;OR;COMPOSITE_TEST;<Unused>;TEST @Value(user_attribute_name) = @UpperCase(@Value(user_attribute_name))'1'BOOL_OP;OR;COMPOSITE_TEST;<Unused>;TEST @Value(user_attribute_name) = @LowerCase(@Value(user_attribute_name))'2'BOOL_OP;OR;COMPOSITE_TEST;<Unused>;TEST @Value(user_attribute_name) = @FullTitleCase(@Value(user_attribute_name))'4'FME_NUM_CONDITIONS4___
    -> DuplicateFilter
Note: Keep only 1 of each case type per FT
DuplicateFilter
    INPUT_ORDERED_CHOICE = No
    KEYATTR = CaseCount feature_type_id
    UNIQUE -> Aggregator
Note: Aggregate by FT ID, summing CaseCount / Sum / Mix / 1 / UPPERCASE only / 2 / lowercase only / 3 / Mix UPPERCASE + lowercase / 4 / Full Title Case only / 5 / Full Title Case + UPPERCASE / 6 / Full Title Case + lowercase / 7 / Full Title Case + UPPERCASE + lowercase / 8 / Title case only / 9 / Title case + UPPERCASE / 10 / Title case + lowercase / 11 / Title case + UPPERCASE + lowercase / 12 / Title case + Full Title Case / 13 / Title Case + Full Title Case + UPPERCASE / 14 / Title Case + Full Title Case + lowercase / 15 / Title Case + Full Title Case + UPPERCASE + lowercase
Aggregator
    ACCUM_ATTRS_NAME = Get Attributes From One Representative Feature
    AGGREGATE_TYPE = Homogeneous Collection (If Possible)
    GROUP_BY = feature_type_id
    MODE = Geometry - Assemble One Level
    ORDERED = No
    SEP = ,
    SUM = CaseCount
    AGGREGATE -> Tester_19
Note: Filter out sums 1, 2, 4, 8, which are one case type only
Tester_19
    BOOL_OP = OR
    TEST_CLAUSE:
      TEST @Value(CaseCount) = 1
      TEST @Value(CaseCount) = 2
      TEST @Value(CaseCount) = 4
      TEST @Value(CaseCount) = 8
    FAILED -> FeatureMerger_11 [REQUESTOR]
Note: Get writer info to add to HTML
FeatureMerger_11
    ATTR_ACCUM_MODE = Merge Supplier
    ATTR_CONFLICT_RES = Use Requestor
    IGNORE_NULLS = No
    JOIN_KEYS = @Value(writer_id) @Value(writer_id) AUTO
    MERGE_TYPE = Attributes Only
    PROCESS_DUPS = No
    REJECT_NULL_MISSING_KEYS = No
    SUPPLIERS_FIRST = No
    MERGED -> AttributeManager_66
    MERGED -> NoFeaturesTester_18
AttributeManager_66
    ATTR_TABLE:
      SET_TO AttrNameCaseWarning = FME_CONDITIONAL:DEFAULT_VALUE'_FME_NO_OP_'BOOL_OP;OR;COMPOSITE_TEST;<Unused>;TEST @Value(CaseCount) = 3'<strong>WARNING:</strong> This workspace contains a writer  - <i>@Value(writer_name) (@Value(writer_keyword))</i> - with a feature type - @Value(writer_feature_type_name) - that has attribute names with mixed cases (UPPERCASE, lowercase).<br>'BOOL_OP;OR;COMPOSITE_TEST;<Unused>;TEST @Value(CaseCount) = 5'<strong>WARNING:</strong> This workspace contains a writer  - <i>@Value(writer_name) (@Value(writer_keyword))</i> - with a feature type - @Value(writer_feature_type_name) - that has attribute names with mixed cases (Full Title Case, UPPERCASE).<br>'BOOL_OP;OR;COMPOSITE_TEST;<Unused>;TEST @Value(CaseCount) = 6'<strong>WARNING:</strong> This workspace contains a writer  - <i>@Value(writer_name) (@Value(writer_keyword))</i> - with a feature type - @Value(writer_feature_type_name) - that has attribute names with mixed cases (Full Title Case, lowercase).<br>'BOOL_OP;OR;COMPOSITE_TEST;<Unused>;TEST @Value(CaseCount) = 7'<strong>WARNING:</strong> This workspace contains a writer  - <i>@Value(writer_name) (@Value(writer_keyword))</i> - with a feature type - @Value(writer_feature_type_name) - that has attribute names with mixed cases (Full Title Case, UPPERCASE, lowercase).<br>'BOOL_OP;OR;COMPOSITE_TEST;<Unused>;TEST @Value(CaseCount) = 9'<strong>WARNING:</strong> This workspace contains a writer  - <i>@Value(writer_name) (@Value(writer_keyword))</i> - with a feature type - @Value(writer_feature_type_name) - that has attribute names with mixed cases (Title case, UPPERCASE).<br>'BOOL_OP;OR;COMPOSITE_TEST;<Unused>;TEST @Value(CaseCount) = 10'<strong>WARNING:</strong> This workspace contains a writer  - <i>@Value(writer_name) (@Value(writer_keyword))</i> - with a feature type - @Value(writer_feature_type_name) - that has attribute names with mixed cases (Title case, lowercase).<br>'BOOL_OP;OR;COMPOSITE_TEST;<Unused>;TEST @Value(CaseCount) = 11'<strong>WARNING:</strong> This workspace contains a writer  - <i>@Value(writer_name) (@Value(writer_keyword))</i> - with a feature type - @Value(writer_feature_type_name) - that has attribute names with mixed cases (Title case, UPPERCASE, lowercase).<br>'BOOL_OP;OR;COMPOSITE_TEST;<Unused>;TEST @Value(CaseCount) = 12'<strong>WARNING:</strong> This workspace contains a writer  - <i>@Value(writer_name) (@Value(writer_keyword))</i> - with a feature type - @Value(writer_feature_type_name) - that has attribute names with mixed cases (Title case, Full Title Case).<br>'BOOL_OP;OR;COMPOSITE_TEST;<Unused>;TEST @Value(CaseCount) = 13'<strong>WARNING:</strong> This workspace contains a writer  - <i>@Value(writer_name) (@Value(writer_keyword))</i> - with a feature type - @Value(writer_feature_type_name) - that has attribute names with mixed cases (Title case, Full Title Case, UPPERCASE).<br>'BOOL_OP;OR;COMPOSITE_TEST;<Unused>;TEST @Value(CaseCount) = 14'<strong>WARNING:</strong> This workspace contains a writer  - <i>@Value(writer_name) (@Value(writer_keyword))</i> - with a feature type - @Value(writer_feature_type_name) - that has attribute names with mixed cases (Title case, Full Title Case, lowercase).<br>'BOOL_OP;OR;COMPOSITE_TEST;<Unused>;TEST @Value(CaseCount) = 15'<strong>WARNING:</strong> This workspace contains a writer  - <i>@Value(writer_name) (@Value(writer_keyword))</i> - with a feature type - @Value(writer_feature_type_name) - that has attribute names with mixed cases (Title case, Full Title Case, UPPERCASE, lowercase).<br>'FME_NUM_CONDITIONS12___
      SET_TO AttrNameCaseRec = <strong>Recommendation:</strong> Although a mix of cases rarely breaks the rules of a format - a mix of Title case and Full Title Case in particular can just be CamelCase - it's better to stick to a single naming case convention.<br>
      SET_TO WarnMsg = 1
    -> HTMLReportGenerator_37
    -> Junction_66
Note: Summary
Junction_66
    -> Junction_8
HTMLReportGenerator_37
    CONTENT_LIST = HEADER LIST HEADER
    PAGE_CONFIG = HEADER{{TEXT;Writer Feature Type Attribute Names;HEADER;H4;ALIGNMENT;LEFT;COLOR;0,0,0;FME_CONTROLLER_QUERY_FILE;transformers\dependencies\html5\Header.fme}}LIST{{ATTR;AttrNameCaseWarning;STYLE;NONE;COLOR;255,170,0;BADGE;;FME_CONTROLLER_QUERY_FILE;transformers\dependencies\html5\List.fme}}HEADER{{TEXT;@Value(AttrNameCaseRec);HEADER;NO;ALIGNMENT;LEFT;COLOR;0,0,0;FME_CONTROLLER_QUERY_FILE;transformers\dependencies\html5\Header.fme}}
    -> AttributeManager_67
NoFeaturesTester_18
    NoInput -> AttributeManager_80
Note: Pass
AttributeManager_80
    ATTR_TABLE = SET_TO AttrNameCaseWarning = <strong>PASS:</strong> This workspace contains no writers with a feature type that has attribute names with mixed cases.
    -> HTMLReportGenerator_46
HTMLReportGenerator_46
    CONTENT_LIST = HEADER LIST
    PAGE_CONFIG = HEADER{{TEXT;Writer Feature Type Attribute Names;HEADER;H4;ALIGNMENT;LEFT;COLOR;0,0,0;FME_CONTROLLER_QUERY_FILE;transformers\dependencies\html5\Header.fme}}LIST{{ATTR;AttrNameCaseWarning;STYLE;NONE;COLOR;0,255,0;BADGE;;FME_CONTROLLER_QUERY_FILE;transformers\dependencies\html5\List.fme}}
    -> AttributeManager_67
Note: SubOrder=5
AttributeManager_67
    ATTR_TABLE = SET_TO SubOrder = 5
    -> Junction_67
Note: LocalOutput
Junction_67
    -> Junction_54

Bookmark: 6.3: Dangling Writers
FeatureMerger_2
    ATTR_ACCUM_MODE = Merge Supplier
    ATTR_CONFLICT_RES = Use Requestor
    CONNECT_Z_MODE = First Wins
    GEOM_TYPE = Build Polygons
    IGNORE_NULLS = No
    JOIN_KEYS = @Value(writer_id) @Value(writer_id) AUTO
    MERGE_COUNT_ATTR = NumFeatureTypes
    MERGE_TYPE = Attributes Only
    PROCESS_DUPS = Yes
    REJECT_NULL_MISSING_KEYS = No
    SUPPLIERS_FIRST = No
    NOT_MERGED -> NoFeaturesTester_5
NoFeaturesTester_5
    NoInput -> AttributeManager_38
    -> StatisticsCalculator_4
StatisticsCalculator_4
    COMPUTE_HISTOGRAM = NO
    COUNT_ATTR = DanglingWriters
    PREPEND_ATTR_NAME_CHOICE = For multiple results only
    STATS_ATTRS = writer_id
    COMPLETE -> AttributeManager_37
Note: Readers without a Feature Type
AttributeManager_37
    ATTR_TABLE:
      SET_TO DanglingWriterText = <strong>WARNING:</strong> This workspace contains a "dangling writer", <i> @Value(writer_name) (@Value(writer_keyword)).</i><br>
      SET_TO WarnMsg = 1
      SET_TO DanglingWriterRec = <strong>Recommendation:</strong> A dangling writer is one without feature types. These are not generally bad, but can cause performance issues and so should be avoided for that reason.<br>
    -> HTMLReportGenerator_19
    -> Junction_32
Note: Summary
Junction_32
    -> Junction_8
HTMLReportGenerator_19
    CONTENT_LIST = HEADER LIST HEADER
    PAGE_CONFIG = HEADER{{TEXT;Dangling Writers: @Value(DanglingWriters);HEADER;H4;ALIGNMENT;LEFT;COLOR;0,0,0;FME_CONTROLLER_QUERY_FILE;transformers\dependencies\html5\Header.fme}}LIST{{ATTR;DanglingWriterText;STYLE;NONE;COLOR;255,170,0;BADGE;;FME_CONTROLLER_QUERY_FILE;transformers\dependencies\html5\List.fme}}HEADER{{TEXT;@Value(DanglingWriterRec);HEADER;NO;ALIGNMENT;LEFT;COLOR;0,0,0;FME_CONTROLLER_QUERY_FILE;transformers\dependencies\html5\Header.fme}}
    -> AttributeManager_42
AttributeManager_38
    ATTR_TABLE = SET_TO DanglingWriterText = <strong>PASS:</strong> This workspace contains zero "dangling writers", writers without an attached feature type.
    -> HTMLReportGenerator_20
HTMLReportGenerator_20
    CONTENT_LIST = HEADER LIST
    PAGE_CONFIG = HEADER{{TEXT;Dangling Writers: 0;HEADER;H4;ALIGNMENT;LEFT;COLOR;0,0,0;FME_CONTROLLER_QUERY_FILE;transformers\dependencies\html5\Header.fme}}LIST{{ATTR;DanglingWriterText;STYLE;NONE;COLOR;0,255,0;BADGE;;FME_CONTROLLER_QUERY_FILE;transformers\dependencies\html5\List.fme}}
    -> AttributeManager_42
Note: SubOrder:3
AttributeManager_42
    ATTR_TABLE = SET_TO SubOrder = 3
    -> Junction_58
Note: Local Output
Junction_58
    -> Junction_54

Bookmark: 6.4: Check for odd characters in Feature Type Names
Note: Regex to check for possibly invalid characters
StringSearcher
    CASE = no
    MATCHED_RESULT_ATTR = _first_match
    REGEXP = [^A-Za-z0-9 ]
    STRING_TO_SEARCH = @Value(writer_feature_type_name)
    MATCHED -> StatisticsCalculator_12
    MATCHED -> NoFeaturesTester_17
StatisticsCalculator_12
    COMPUTE_HISTOGRAM = NO
    COUNT_ATTR = NumOddFTNames
    PREPEND_ATTR_NAME_CHOICE = For multiple results only
    STATS_ATTRS = feature_type_id
    COMPLETE -> AttributeManager_70
AttributeManager_70
    ATTR_TABLE:
      SET_TO OddFTNameText = <strong>WARNING:</strong> This workspace contains a feature type, <i>@Value(writer_feature_type_name)</i>, whose name contains characters outside A-Z and 0-9<br>
      SET_TO OddFTNameRec = <strong>Recommendation:</strong> The Workbench interface tries to prevent feature types being given invalid names. However, it's still worth checking to ensure all feature types have names that are valid for the format they are being written to.<br>
      SET_TO WarnMsg = 1
    -> HTMLReportGenerator_39
    -> Junction_68
Note: Summary
Junction_68
    -> Junction_8
HTMLReportGenerator_39
    CONTENT_LIST = HEADER LIST HEADER
    PAGE_CONFIG = HEADER{{TEXT;Odd Feature Type Names: @Value(NumOddFTNames);HEADER;H4;ALIGNMENT;LEFT;COLOR;0,0,0;FME_CONTROLLER_QUERY_FILE;transformers\dependencies\html5\Header.fme}}LIST{{ATTR;OddFTNameText;STYLE;NONE;COLOR;255,170,0;BADGE;;FME_CONTROLLER_QUERY_FILE;transformers\dependencies\html5\List.fme}}HEADER{{TEXT;@Value(OddFTNameRec);HEADER;NO;ALIGNMENT;LEFT;COLOR;0,0,0;FME_CONTROLLER_QUERY_FILE;transformers\dependencies\html5\Header.fme}}
    -> AttributeManager_71
NoFeaturesTester_17
    NoInput -> AttributeManager_79
Note: Pass
AttributeManager_79
    ATTR_TABLE = SET_TO OddFTNameText = <strong>PASS:</strong> This workspace contains no feature types whose name contains characters outside A-Z and 0-9
    -> HTMLReportGenerator_45
HTMLReportGenerator_45
    CONTENT_LIST = HEADER LIST
    PAGE_CONFIG = HEADER{{TEXT;Odd Feature Type Names: 0;HEADER;H4;ALIGNMENT;LEFT;COLOR;0,0,0;FME_CONTROLLER_QUERY_FILE;transformers\dependencies\html5\Header.fme}}LIST{{ATTR;OddFTNameText;STYLE;NONE;COLOR;0,255,0;BADGE;;FME_CONTROLLER_QUERY_FILE;transformers\dependencies\html5\List.fme}}
    -> AttributeManager_71
Note: SubOrder: 4
AttributeManager_71
    ATTR_TABLE = SET_TO SubOrder = 4
    -> Junction_69
Note: Local Output
Junction_69
    -> Junction_54

Bookmark: 6.7: Automatically Published Destination Parameters
Note: PublishedParameters
Junction_74
    -> Tester_20
Tester_20
    BOOL_OP = OR
    TEST_CLAUSE = TEST @Value(published_parameter_name) BEGINS_WITH DestDataset_
    PASSED -> AttributeManager_74
    PASSED -> NoFeaturesTester_15
AttributeManager_74
    ATTR_TABLE:
      SET_TO PubDestParamText = <strong>WARNING:</strong> This workspace contains an automatically published destination dataset parameter: <i>@Value(published_parameter_name)</i>.
      SET_TO PubDestParamRec = <strong>Recommendation:</strong> Such parameters are published automatically by FME but are not always needed. If not required they should be deleted, so there is no confusion about what destination datasets are named.
      SET_TO WarnMsg = 1
    -> HTMLReportGenerator_41
    -> Junction_75
Note: Summary
Junction_75
    -> Junction_8
HTMLReportGenerator_41
    CONTENT_LIST = HEADER LIST HEADER
    PAGE_CONFIG = HEADER{{TEXT;Automatic Destination Dataset Published Parameters;HEADER;H4;ALIGNMENT;LEFT;COLOR;0,0,0;FME_CONTROLLER_QUERY_FILE;transformers\dependencies\html5\Header.fme}}LIST{{ATTR;PubDestParamText;STYLE;NONE;COLOR;255,170,0;BADGE;;FME_CONTROLLER_QUERY_FILE;transformers\dependencies\html5\List.fme}}HEADER{{TEXT;@Value(PubDestParamRec);HEADER;NO;ALIGNMENT;LEFT;COLOR;0,0,0;FME_CONTROLLER_QUERY_FILE;transformers\dependencies\html5\Header.fme}}
    -> AttributeManager_75
NoFeaturesTester_15
    NoInput -> AttributeManager_77
AttributeManager_77
    ATTR_TABLE = SET_TO PubDestParamText = <strong>PASS:</strong> This workspace contains no automatically published destination dataset parameters.
    -> HTMLReportGenerator_43
HTMLReportGenerator_43
    CONTENT_LIST = HEADER LIST
    PAGE_CONFIG = HEADER{{TEXT;Automatic Destination Dataset Published Parameters;HEADER;H4;ALIGNMENT;LEFT;COLOR;0,0,0;FME_CONTROLLER_QUERY_FILE;transformers\dependencies\html5\Header.fme}}LIST{{ATTR;PubDestParamText;STYLE;NONE;COLOR;0,255,0;BADGE;;FME_CONTROLLER_QUERY_FILE;transformers\dependencies\html5\List.fme}}
    -> AttributeManager_75
AttributeManager_75
    ATTR_TABLE = SET_TO SubOrder = 7
    -> Junction_76
Note: Local Output
Junction_76
    -> Junction_54

Bookmark: 6.6: Writer Coordinate System Set without Reader Coordinate System Set (or CSSetter transformer)
Note: Writer Parameters
Junction_49
    -> Tester_16
Tester_16
    BOOL_OP = AND
    TEST_CLAUSE:
      TEST @Value(writer_parameter_name) = COORDSYS
      TEST @Value(writer_parameter_value) ATTRIBUTE_HAS_VALUE ""
    PASSED -> StatisticsCalculator_11
StatisticsCalculator_11
    COMPUTE_HISTOGRAM = NO
    COUNT_ATTR = NumWritersCoordSysSet
    PREPEND_ATTR_NAME_CHOICE = For multiple results only
    STATS_ATTRS = writer_id
    SUMMARY -> FeatureMerger_9 [REQUESTOR]
Note: Reader Parameters
Junction_50
    -> Tester_17
Tester_17
    BOOL_OP = AND
    TEST_CLAUSE:
      TEST @Value(reader_parameter_name) = COORDSYS
      TEST @Value(reader_parameter_value) ATTRIBUTE_HAS_VALUE ""
    PASSED -> FeatureMerger_9 [SUPPLIER]
Note: Transformers
Junction_61
    -> Tester_18
Note: Check for CoordinateSystemSetter
Tester_18
    BOOL_OP = OR
    TEST_CLAUSE = TEST @Value(transformer_type) = CoordinateSystemSetter
    PASSED -> FeatureMerger_9 [SUPPLIER]
FeatureMerger_9
    ATTR_ACCUM_MODE = Merge Supplier
    ATTR_CONFLICT_RES = Use Requestor
    IGNORE_NULLS = No
    JOIN_KEYS = 1 1 AUTO
    MERGE_TYPE = Attributes Only
    PROCESS_DUPS = No
    REJECT_NULL_MISSING_KEYS = No
    SUPPLIERS_FIRST = No
    NOT_MERGED -> AttributeManager_64
    NOT_MERGED -> NoFeaturesTester_16
NoFeaturesTester_16
    NoInput -> AttributeManager_78
Note: Pass
AttributeManager_78
    ATTR_TABLE = SET_TO CoordSysMismatchWarning = <strong>PASS:</strong> This workspace contains no writer with a coordinate system set that relies on reader coordinate system information being stored in the source dataset.
    -> HTMLReportGenerator_44
HTMLReportGenerator_44
    CONTENT_LIST = HEADER LIST
    PAGE_CONFIG = HEADER{{TEXT;Coordinate System Parameter Mismatch;HEADER;H4;ALIGNMENT;LEFT;COLOR;0,0,0;FME_CONTROLLER_QUERY_FILE;transformers\dependencies\html5\Header.fme}}LIST{{ATTR;CoordSysMismatchWarning;STYLE;NONE;COLOR;255,170,0;BADGE;;FME_CONTROLLER_QUERY_FILE;transformers\dependencies\html5\List.fme}}
    -> AttributeManager_65
AttributeManager_64
    ATTR_TABLE:
      SET_TO CoordSysMismatchWarning = FME_CONDITIONAL:DEFAULT_VALUE'<strong>WARNING:</strong> This workspace contains @Value(NumWritersCoordSysSet) writers with a coordinate system set, but no readers have a coordinate system and there is no CoordinateSystemSetter transformer.<br>'BOOL_OP;OR;COMPOSITE_TEST;<Unused>;TEST @Value(NumWritersCoordSysSet) = 1'<strong>WARNING:</strong> This workspace contains a writer with a coordinate system set, but no readers have a coordinate system and there is no CoordinateSystemSetter transformer.<br>'FME_NUM_CONDITIONS2___
      SET_TO CoordSysMismatchRec = <strong>Recommendation:</strong> Ensure that your source datasets contain coordinate system information, set a reader coordinate system, or use a CoordinateSystemSetter transformer.<br>The translation will fail if FME does not know from which coordinate system to reproject the data.<br>
      SET_TO WarnMsg = 1
    -> Junction_53
    -> HTMLReportGenerator_36
Note: Summary
Junction_53
    -> Junction_8
HTMLReportGenerator_36
    CONTENT_LIST = HEADER LIST HEADER
    PAGE_CONFIG = HEADER{{TEXT;Coordinate System Parameter Mismatch;HEADER;H4;ALIGNMENT;LEFT;COLOR;0,0,0;FME_CONTROLLER_QUERY_FILE;transformers\dependencies\html5\Header.fme}}LIST{{ATTR;CoordSysMismatchWarning;STYLE;NONE;COLOR;255,170,0;BADGE;;FME_CONTROLLER_QUERY_FILE;transformers\dependencies\html5\List.fme}}HEADER{{TEXT;@Value(CoordSysMismatchRec);HEADER;NO;ALIGNMENT;LEFT;COLOR;0,0,0;FME_CONTROLLER_QUERY_FILE;transformers\dependencies\html5\Header.fme}}
    -> AttributeManager_65
Note: SubOrder=6
AttributeManager_65
    ATTR_TABLE = SET_TO SubOrder = 6
    -> Junction_59
Note: Local Output
Junction_59
    -> Junction_54

Bookmark: Report Summary
Note: Summary
Junction_8
    -> StatisticsCalculator
StatisticsCalculator
    COMPUTE_HISTOGRAM = NO
    PREPEND_ATTR_NAME_CHOICE = For multiple results only
    STATS_ATTRS = ErrorMsg
    SUM_ATTR = ErrorTotal
    COMPLETE -> StatisticsCalculator_2
StatisticsCalculator_2
    COMPUTE_HISTOGRAM = NO
    PREPEND_ATTR_NAME_CHOICE = For multiple results only
    STATS_ATTRS = WarnMsg
    SUM_ATTR = WarnTotal
    COMPLETE -> Sampler
Sampler
    RATE = 1
    SAMPLE_MODE = No
    SAMPLE_TYPE_LONG = First N Features
    SAMPLED -> AttributeManager_14
Note: Set up Error/Warning syntax
AttributeManager_14
    ATTR_TABLE:
      SET_TO WarnVerb = FME_CONDITIONAL:DEFAULT_VALUE'were'BOOL_OP;OR;COMPOSITE_TEST;<Unused>;TEST @Value(WarnTotal) = 1'was'FME_NUM_CONDITIONS2___
      SET_TO ErrorVerb = FME_CONDITIONAL:DEFAULT_VALUE'were'BOOL_OP;OR;COMPOSITE_TEST;<Unused>;TEST @Value(ErrorTotal) = 1'was'FME_NUM_CONDITIONS2___
      SET_TO WarnNoun = FME_CONDITIONAL:DEFAULT_VALUE'warnings'BOOL_OP;OR;COMPOSITE_TEST;<Unused>;TEST @Value(WarnTotal) = 1'warning'FME_NUM_CONDITIONS2___
      SET_TO ErrorNoun = FME_CONDITIONAL:DEFAULT_VALUE'errors'BOOL_OP;OR;COMPOSITE_TEST;<Unused>;TEST @Value(ErrorTotal) = 1'error'FME_NUM_CONDITIONS2___
    -> HTMLReportGenerator_4
HTMLReportGenerator_4
    CONTENT_LIST = HEADER HEADER HEADER
    PAGE_CONFIG = HEADER{{TEXT;Summary;HEADER;H3;ALIGNMENT;LEFT;COLOR;0,0,0;FME_CONTROLLER_QUERY_FILE;transformers\dependencies\html5\Header.fme}}HEADER{{TEXT;There @Value(ErrorVerb) @Value(ErrorTotal) @Value(ErrorNoun);HEADER;H4;ALIGNMENT;LEFT;COLOR;255,0,0;FME_CONTROLLER_QUERY_FILE;transformers\dependencies\html5\Header.fme}}HEADER{{TEXT;There @Value(WarnVerb) @Value(WarnTotal) @Value(WarnNoun);HEADER;H4;ALIGNMENT;LEFT;COLOR;255,170,0;FME_CONTROLLER_QUERY_FILE;transformers\dependencies\html5\Header.fme}}
    -> AttributeManager_5
AttributeManager_5
    ATTR_TABLE = SET_TO ReportOrder = 9999
    -> Junction_5
Note: To Output (Sorter)
Junction_5
    -> Sorter

Bookmark: Collate and Output Report
Note: Output
Junction_2
    -> Sorter
Sorter
    SORT_PARM = ReportOrder NUMERIC ASCENDING
    SORTED -> StringReplacer_2
StringReplacer_2
    CASE = NO
    FIND_TEXT = &lt;strong&gt;
    NO_MATCH = _FME_NO_OP_
    REGEXP = NO
    REPLACE_TEXT = <strong>
    SRC_ATTRS = html_content
    -> StringReplacer
StringReplacer
    CASE = NO
    FIND_TEXT = &lt;/strong&gt;
    NO_MATCH = _FME_NO_OP_
    REGEXP = NO
    REPLACE_TEXT = </strong>
    SRC_ATTRS = html_content
    -> StringReplacer_3
StringReplacer_3
    CASE = NO
    FIND_TEXT = &lt;br&gt;
    NO_MATCH = _FME_NO_OP_
    REGEXP = NO
    REPLACE_TEXT = <br>
    SRC_ATTRS = html_content
    -> StringReplacer_5
Note: StringReplacers to clean up WWJD encoding and replace with true HTML tags
StringReplacer_5
    CASE = NO
    FIND_TEXT = &lt;i&gt;
    NO_MATCH = _FME_NO_OP_
    REGEXP = NO
    REPLACE_TEXT = <i>
    SRC_ATTRS = html_content
    -> StringReplacer_6
StringReplacer_6
    CASE = NO
    FIND_TEXT = &lt;/i&gt;
    NO_MATCH = _FME_NO_OP_
    REGEXP = NO
    REPLACE_TEXT = </i>
    SRC_ATTRS = html_content
    -> StringReplacer_4
Note: remove empty list tags
StringReplacer_4
    CASE = NO
    FIND_TEXT = <li >None</li>
    NO_MATCH = _FME_NO_OP_
    REGEXP = NO
    SRC_ATTRS = html_content
    -> HTMLLayouter
HTMLLayouter
    DIV_STYLE = VERTICAL
    LAYOUT = VERTICAL
    -> HTML (writer HTML_1)
HTML (writer HTML_1)
    attributes: html_content buffer

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

Input (input)
    -> Output (output)
    -> Sampler
Note: Take the first input feature
Sampler
    RATE = 1
    SAMPLE_MODE = No
    SAMPLE_TYPE_LONG = First N Features
    SAMPLED -> StatisticsCalculator
Output (output)
Creator
    GEOMTYPE = Geometry Object
    NUM = 1
    CREATED -> StatisticsCalculator
Note: Count received features
StatisticsCalculator
    COMPUTE_HISTOGRAM = NO
    COUNT_ATTR = NFT_count
    PREPEND_ATTR_NAME_CHOICE = For multiple results only
    STATS_ATTRS = no_features
    SUMMARY -> Tester_2
Note: If the number of features is equal / to 1, we had no feature coming / through the Input port
Tester_2
    BOOL_OP = OR
    TEST_CLAUSE = TEST @Value(NFT_count) = 1
    PASSED -> AttributeCreator
Note: Provide an attribute for filtering
AttributeCreator
    ATTR_TABLE = SET_TO no_features = true
    -> NoInput (output)
NoInput (output)
