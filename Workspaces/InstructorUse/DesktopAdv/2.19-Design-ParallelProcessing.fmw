FME workspace 2.19-Design-ParallelProcessing.fmw

Parameters:
- SourceDataset_ACAD = C:\FMEData2018\Data\Transportation\CompleteRoads.dwg   # Source Autodesk AutoCAD DWG/DXF File(s)
- FEATURE_TYPES =

Readers:
- ACAD_1: ACAD from $(SourceDataset_ACAD)

Arterial (reader ACAD_1)
    attributes: From_HBlock char(10), HBlock char(27), OneWay char(2), StreetId number(6,0), StreetName char(19)
    -> ModuloCounter
    -> Bufferer
Note: Bufferer [Bufferer Version 14] / Transformer: / Group By: StreetName / Parallel Processing: Moderate / Input Ordered: No
Note: When inspecting the results (using Cached Data), use the Filter function in the Data Inspector to show one group at a time. This shows how the groups are formed.
Bufferer
    ANGLE = 22.5
    CAP_STYLE = Round
    CORNER_STYLE = Round
    GROUP_BY = StreetName
    MODE = AREA
    OFFSET = 25
Note: ModuloCounter [ModuloCounter Version 1] / Parameters: / Count Output Attribute: _modulo_count / Counter Name: modcounter / Count Maximum: 4
Note: The ModuloCounter creates four groups of approximately equal size.
ModuloCounter
    CNT_ATTR = _modulo_count
    DOMAIN = modcounter
    MOD = 4
    -> Bufferer_2
Note: Bufferer [Bufferer Version 14] / Transformer: / Group By: _modulo_count / Parallel Processing: Moderate / Input Ordered: No
Bufferer_2
    ANGLE = 22.5
    CAP_STYLE = Round
    CORNER_STYLE = Round
    GROUP_BY = _modulo_count
    MODE = AREA
    OFFSET = 20
    BUFFERED -> Dissolver_2
Note: In this example, road features are being buffered. Parallel processing is applied. / In the above example, the groups are formed by street names. The user wants one buffer per street. / In the example below the groups are created using a ModuloCounter. The user wants just one buffer for the whole city. / The first example works, but because it is creating more groups than is optimal - and groups of uneven sizes - performance is not great. / The second example works because the order/grouping of features does not matter, as long as they get dissolved at the end. Four groups are created assuming we are on a quad-core machine and using moderate processing. / It might not make much improvement in performance (in fact it might even be slower) but larger data volumes make the technique worthwhile.
Note: The Dissolver in this case merges all the buffered features into a single, city-wide, buffer.
Dissolver_2
    ACCUM_INPUT_ATTRS = Use Attributes From One Feature
    CLEANING_TOLERANCE = None
    CONNECT_Z_MODE = First Wins
    DEAGGREGATE_INPUT = Yes
    NO_OVRLP = No
