FME workspace 5.02.CustomTransformers-Ports.fmw

Parameters:
- SourceDataset_MITAB = c:\FMEData\Data\Parks\Parks.tab   # Source MapInfo TAB File(s)
- SourceDataset_GEOTIFF = ""c:\FMEData\Data\Orthophotos\02-03-HI.tif" "c:\FMEData\Data\Orthophotos\02-03-JK.tif" "c:\FMEData\Data\Orthophotos\02-03-LM.tif" "c:\FMEData\Data\Orthophotos\02-03-NO.tif" "c:\FMEData\Data\Orthophotos\04-05-HI.tif" "c:\FMEData\Data\Orthophotos\04-05-JK.tif" "c:\FMEData\Data\Orthophotos\04-05-LM.tif" "c:\FMEData\Data\Orthophotos\04-05-NO.tif" "c:\FMEData\Data\Orthophotos\04-05-PQ.tif" "c:\FMEData\Data\Orthophotos\04-05-RS.tif" "c:\FMEData\Data\Orthophotos\06-07-HI.tif" "c:\FMEData\Data\Orthophotos\06-07-JK.tif" "c:\FMEData\Data\Orthophotos\06-07-LM.tif" "c:\FMEData\Data\Orthophotos\06-07-NO.tif" "c:\FMEData\Data\Orthophotos\06-07-PQ.tif" "c:\FMEData\Data\Orthophotos\06-07-RS.tif" "c:\FMEData\Data\Orthophotos\08-09-HI.tif" "c:\FMEData\Data\Orthophotos\08-09-JK.tif" "c:\FMEData\Data\Orthophotos\08-09-LM.tif" "c:\FMEData\Data\Orthophotos\08-09-NO.tif" "c:\FMEData\Data\Orthophotos\08-09-PQ.tif" "c:\FMEData\Data\Orthophotos\08-09-RS.tif" "c:\FMEData\Data\Orthophotos\10-11-HI.tif" "c:\FMEData\Data\Orthophotos\10-11-JK.tif" "c:\FMEData\Data\Orthophotos\10-11-LM.tif" "c:\FMEData\Data\Orthophotos\10-11-NO.tif" "c:\FMEData\Data\Orthophotos\10-11-PQ.tif" "c:\FMEData\Data\Orthophotos\10-11-RS.tif" "c:\FMEData\Data\Orthophotos\12-13-HI.tif" "c:\FMEData\Data\Orthophotos\12-13-JK.tif" "c:\FMEData\Data\Orthophotos\12-13-LM.tif" "c:\FMEData\Data\Orthophotos\12-13-NO.tif" "c:\FMEData\Data\Orthophotos\12-13-PQ.tif" "c:\FMEData\Data\Orthophotos\12-13-RS.tif" "c:\FMEData\Data\Orthophotos\14-15-HI.tif" "c:\FMEData\Data\Orthophotos\14-15-JK.tif" "c:\FMEData\Data\Orthophotos\14-15-LM.tif" "c:\FMEData\Data\Orthophotos\14-15-NO.tif" "c:\FMEData\Data\Orthophotos\14-15-PQ.tif" "c:\FMEData\Data\Orthophotos\14-15-RS.tif""   # Source GeoTIFF File(s)
- FEATURE_TYPES =

Readers:
- MITAB_2: MITAB from $(SourceDataset_MITAB)
- GEOTIFF_2: GEOTIFF from $(SourceDataset_GEOTIFF)

Parks (reader MITAB_2)
    attributes: ParkId smallint, RefParkId smallint, ParkName char(40), NeighborhoodName char(40), VisitorCount smallint, TreeCount smallint, DogPark char(1), Washrooms char(1), SpecialFeatures char(1)
Note: GeoTIFF
GEOTIFF (reader GEOTIFF_2)
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> RasterBandAdder
RasterBandAdder
    CELL_VALUE = 255
    INTERPRETATION = Alpha8
Note: Instructor Notes / Section 5.02: Go to the transformer definition and explain how it includes no input/output ports. / Show how to add new ports. / Demonstrate how multiple input and output ports can be added and used. / Discuss the <Rejected> port and its use in FME
RasterProcessor

FME custom transformer RasterProcessor

AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> FeatureColorSetter
FeatureColorSetter
    COLOR = 0,0.666667,0
    FILL_COLOR = 0.666667,1,0.498039
    MODE = Fixed
    COLORED -> VectorOnRasterOverlayer [VECTOR]
VectorOnRasterOverlayer
    ALPHA = 0.5
    ANTI_ALIASING = No
    COMPOSITE_USING_ALPHA_BAND = Yes
    TOLERANCE = 0.5
