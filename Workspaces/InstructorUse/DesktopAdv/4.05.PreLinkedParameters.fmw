FME workspace 4.05.PreLinkedParameters.fmw

Parameters:
- SourceDataset_MITAB = c:\FMEData\Data\Parks\Parks.tab   # Source MapInfo TAB File(s)
- DestDataset_GML = c:\FMEData\Output\Training\Parks.gml   # Destination Geography Markup Language (GML) File

Readers:
- MITAB_1: MITAB from $(SourceDataset_MITAB)

Writers:
- GML_1: GML to $(DestDataset_GML)

Note: Instructor Notes / Section 4.05: This workspace is exactly as it was generated. Note the user parameters created automatically. / Demonstrate how to remove these parameters if they are not required.

Bookmark: Reader Feature Types
Parks (reader MITAB_1)
    attributes: ParkId smallint, RefParkId smallint, ParkName char(40), NeighborhoodName char(40), VisitorCount smallint, TreeCount smallint, DogPark char(1), Washrooms char(1), SpecialFeatures char(1)
    -> Parks (writer GML_1)

Bookmark: Writer Feature Types
Parks (writer GML_1)
    attributes: ParkId xml_int16, RefParkId xml_int16, ParkName xml_char(40), NeighborhoodName xml_char(40), VisitorCount xml_int16, TreeCount xml_int16, DogPark xml_char(1), Washrooms xml_char(1), SpecialFeatures xml_char(1)
