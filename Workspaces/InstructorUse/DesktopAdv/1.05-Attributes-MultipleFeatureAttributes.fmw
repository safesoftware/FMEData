FME workspace 1.05-Attributes-MultipleFeatureAttributes.fmw

Parameters:
- SourceDataset_XLSXR = c:\FMEData\Data\Planning\BusinessLicenses.xlsx   # Source Microsoft Excel File(s)

Readers:
- XLSXR_1: XLSXR from $(SourceDataset_XLSXR)

Business_Licences (reader XLSXR_1)
    attributes: RecordID number(4,0), LicenceRSN number(8,0), LicenceNumber char(10), BusinessTradeName char(41), Status char(21), IssuedDate char(20), ExpiredDate char(20), BusinessType char(14), Number char(8), Street char(32), City char(19), Province char(3), Country char(4), PostalCode char(11), LocalArea char(29), NumberOfEmployees number(5,0), FeePaid number(8,2)
    -> Tester
Tester
    BOOL_OP = OR
    COMPOSITE_TEST = 1
    TEST_CLAUSE = TEST IssuedDate ATTRIBUTE_HAS_A_VALUE ""
    TEST_MODE = TEST
    PASSED -> DateTimeConverter
DateTimeConverter
    DATETIME_ATTR = IssuedDate
    OUT_FORMAT = FME
    PASSTHROUGH = NO
    REPAIR_INPUT = YES
    -> Sorter
Sorter
    SORT_PARM = IssuedDate NUMERIC DESCENDING
    SORTED -> AttributeManager
Note: Instructor Notes / Section 1.05: / This workspace reads a set of records for business licenses, and sorts them into the order they were issued. / The AttributeManager takes the datetime for the previous record, and subtracts it from the current one to determine the time between two licenses being issued. / Examine the AttributeManager parameters. Explain and demonstrate the adjacent feature functionality. Check the result of the first record and explain why it gets that value. Experiment with different settings for handling missing values.
AttributeManager
    ATTR_TABLE = SET_TO TimeOffset = @DateTimeDiff(@Value(IssuedDate),@Value(feature[-1].IssuedDate),Minutes)
    NUM_PRIOR_FEATURES = 1
    NUM_SUBSEQUENT_FEATURES = 0
