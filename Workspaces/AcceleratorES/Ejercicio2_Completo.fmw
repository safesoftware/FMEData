FME workspace Ejercicio2_Completo.fmw

Parameters:
- SourceDataset_CSV2 = C:\FMEData\Data\AcceleratorES\mercadosmunicipales.csv   # Archivos CSV (Comma Separated Value) de Origen
- SourceDataset_SHAPEFILE = C:\FMEData\Data\AcceleratorES\CallejeroMadridOr.shp   # Shapefiles de Esri de Origen
- SourceDataset_XLSXR = C:\FMEData\Data\AcceleratorES\CortesTrafico.xlsx   # Archivos Microsoft Excel de Origen
- DestDataset_XLSXW = C:\FMEData\Output\AcceleratorES\ConversionExcel.xlsx   # Archivo Microsoft Excel de Destino

Readers:
- CSV2_1: CSV2 from $(SourceDataset_CSV2)
- SHAPEFILE_1: SHAPEFILE from $(SourceDataset_SHAPEFILE)
- XLSXR_1: XLSXR from $(SourceDataset_XLSXR)

Writers:
- XLSXW_1: XLSXW to $(DestDataset_XLSXW)

CSV (reader CSV2_1)
    attributes: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
CallejeroMadridOr (reader SHAPEFILE_1)
    attributes: Nombre cal varchar(200), CDMUNI varchar(3), CDVIAL varchar(8), CMUN varchar(10), CODVI varchar(8), VIA_TVIA varchar(6), VIA_PART varchar(6), VIA_LITE varchar(51), NOMBRE varchar(100), HISTORICO varchar(100), VIA_CINE varchar(5)
    -> Hoja1 (writer XLSXW_1)
Hoja1 (writer XLSXW_1)
    attributes: Nombre cal string(200), CDMUNI string(3), CDVIAL string(8), CMUN string(10), CODVI string(8), VIA_TVIA string(6), VIA_PART string(6), VIA_LITE string(51), NOMBRE string(100), HISTORICO string(100), VIA_CINE string(5)
Cortes (reader XLSXR_1)
    attributes: Nombre Calle char(35)
