FME workspace Ex3.1-Complete-Advanced.fmw

Parameters:
- SourceDataset_XLSXR = https://s3.amazonaws.com/FMEData/Interopolis/CaseLocationsDetails_2017_XLS.zip   # Source Microsoft Excel File(s)
- DestDataset_CSV2 = C:\FMEData2020\Output\Training   # Destination CSV (Comma Separated Value) Folder

Readers:
- XLSXR_2: XLSXR from $(SourceDataset_XLSXR)

Writers:
- CSV2_2: CSV2 to $(DestDataset_CSV2)

Tester
    BOOL_OP = OR
    COMPOSITE_TEST = 1
    TEST_CLAUSE = TEST Local_Area ATTRIBUTE_HAS_A_VALUE ""
    TEST_MODE = TEST
    PASSED -> AttributeManager
AttributeManager
    ATTR_TABLE:
      RENAME_SET_VALUE Case_Type > Case Type
      RENAME_SET_VALUE Hundred_Block > Hundred Block
      RENAME_SET_VALUE Street_Name > Street Name
      RENAME_SET_VALUE Local_Area > Local Area
      SET_TO Date = @TimeZoneSet(@Format(%04d,@Value(Year))@Format(%02d,@Value(Month))@Format(%02d,@Value(Day))@Format(%02d,@Value(Hour))@Format(%02d,@Value(Minute))00, local)
    -> 311-requests (writer CSV2_2)

Bookmark: Reader Feature Types
CA18COV1 - Service Request Loca (reader XLSXR_2)
    attributes: Year number(5,0), Month char(255), Day number(2,0), Hour number(3,0), Minute number(3,0), Department char(255), Division char(51), Case_Type char(50), Hundred_Block char(13), Street_Name char(255), Local_Area char(25)
    -> Tester

Bookmark: Writer Feature Types
311-requests (writer CSV2_2)
    attributes: Year string, Month string, Day string, Hour string, Minute string, Department string, Division string, Case Type string, Hundred Block string, Street Name string, Local Area string, Date string
