FME workspace Ex4.1-Complete.fmw

Parameters:
- SourceDataset_XLSXR = https://s3.amazonaws.com/FMEData/Interopolis/CaseLocationsDetails_2017_XLS.zip   # Source Microsoft Excel File(s)
- DestDataset_OGCKML = C:\FMEData2020\Output\Training\311-local-areas.kml   # Destination Google KML File
- SourceDataset_OGCKML = C:\FMEData2020\Data\Boundaries\LocalAreas.kml   # Source Google KML File or URL
- DestDataset_CSV2 = C:\FMEData2020\Output\Training   # Destination CSV (Comma Separated Value) Folder
- SourceDataset_CSV2 = C:\FMEData2020\Resources\311\311-summary.csv   # Source CSV (Comma Separated Value) File(s)

Readers:
- XLSXR_2: XLSXR from $(SourceDataset_XLSXR)
- OGCKML_3: OGCKML from $(SourceDataset_OGCKML)
- CSV2_3: CSV2 from $(SourceDataset_CSV2)

Writers:
- OGCKML_1: OGCKML to $(DestDataset_OGCKML)
- CSV2_1: CSV2 to $(DestDataset_CSV2)

FeatureJoiner
    ATTR_CONFLICT_RES = Use Left
    GEOMETRY_HANDLING = Use Left
    JOIN_KEYS = Name Local Area AUTO
    JOIN_MODE = Inner
    JOINED -> 311-local-areas (writer OGCKML_1)
Tester
    BOOL_OP = OR
    COMPOSITE_TEST = 1
    TEST_CLAUSE = TEST Local_Area ATTRIBUTE_HAS_A_VALUE ""
    TEST_MODE = TEST
    PASSED -> AttributeManager
AttributeManager
    ATTR_TABLE:
      RENAME_SET_VALUE Case_Type > Case Type
      RENAME_SET_VALUE Hundred_Block > Hundred Block
      RENAME_SET_VALUE Street_Name > Street Name
      RENAME_SET_VALUE Local_Area > Local Area
      SET_TO Date = @Value(Year)/@Value(Month)/@Value(Day)
    -> StringReplacer
StringReplacer
    CASE = NO
    FIND_TEXT = Arbutus Ridge
    NO_MATCH = _FME_NO_OP_
    REGEXP = NO
    REPLACE_TEXT = Arbutus-Ridge
    SRC_ATTRS = Local Area
    -> StringReplacer_2
StringReplacer_2
    CASE = NO
    FIND_TEXT = Dunbar Southlands
    NO_MATCH = _FME_NO_OP_
    REGEXP = NO
    REPLACE_TEXT = Dunbar-Southlands
    SRC_ATTRS = Local Area
    -> 311-requests (writer CSV2_1)

Bookmark: Reader Feature Types
local_areas_region (reader OGCKML_3)
    attributes: Name kml_buffer, Description kml_buffer
    -> FeatureJoiner [LEFT]
CSV (reader CSV2_3)
    attributes: Local Area string, 311 Contact Centre string, Business Planning & Services string, CSG - Inspections string, CSG - Licenses & Inspections string, CSG - Licenses string, City Administration string, DBL - Administration string, DBL - Inspections string, DBL - Licensing & Animal Services string, ENG - Office of the Deputy City Engineer string, ENG - Solid Waste string, ENG - Streets string, ENG - Transportation string, ENG - Water & Sewer string, Interdepartmental Initiatives string, Public Safety - Fire string, ZZ OLD - PRB - Planning and Operations string
    -> FeatureJoiner [RIGHT]
CA18COV1 - Service Request Loca (reader XLSXR_2)
    attributes: Year number(5,0), Month char(255), Day number(2,0), Hour number(3,0), Minute number(3,0), Department char(255), Division char(51), Case_Type char(50), Hundred_Block char(13), Street_Name char(255), Local_Area char(25)
    -> Tester

Bookmark: Writer Feature Types
311-local-areas (writer OGCKML_1)
    attributes: Name kml_buffer, Description kml_buffer, Local Area kml_char(255), 311 Contact Centre kml_char(255), Business Planning & Services kml_char(255), CSG - Inspections kml_char(255), CSG - Licenses & Inspections kml_char(255), CSG - Licenses kml_char(255), City Administration kml_char(255), DBL - Administration kml_char(255), DBL - Inspections kml_char(255), DBL - Licensing & Animal Services kml_char(255), ENG - Office of the Deputy City Engineer kml_char(255), ENG - Solid Waste kml_char(255), ENG - Streets kml_char(255), ENG - Transportation kml_char(255), ENG - Water & Sewer kml_char(255), Interdepartmental Initiatives kml_char(255), Public Safety - Fire kml_char(255), ZZ OLD - PRB - Planning and Operations kml_char(255)
311-requests (writer CSV2_1)
    attributes: Year string, Month string, Day string, Hour string, Minute string, Department string, Division string, Case Type string, Hundred Block string, Street Name string, Local Area string, Date string
