FME workspace Exercise5b-Complete.fmw

Parameters:
- SourceDataset_GML = C:\FMEData2014\Data\Boundaries\CoastalZones\CoastalZones.gml   # Source Geography Markup Language (GML) File(s)
- SourceDataset_CDED = C:\FMEData2014\Data\ElevationModel\DEM-Clipped.dem   # Source Canadian Digital Elevation Data (CDED) File(s)
- SourceDataset_FILEGDB_3 = C:\FMEData2015\Data\Addresses\Addresses.gdb   # Source Geodatabase

Readers:
- GML_1: GML from $(SourceDataset_GML)
- CDED_1: CDED from $(SourceDataset_CDED)
- FILEGDB_2: FILEGDB from $(SourceDataset_FILEGDB_3)

Note: PostalAddress: Addresses [FILEGDB]
PostalAddress (reader FILEGDB_2)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> PointOnAreaOverlayer_2 [input 1]
Note: CoastalZones [GML]
_300m (reader GML_1)
    attributes: gml_parent_id xml_buffer, Zone xml_int16, gml_surfaceProperty xml_geometry, gml_multiSurfaceProperty xml_geometry
    -> PointOnAreaOverlayer_2 [input 2]
_200m (reader GML_1)
    attributes: gml_parent_id xml_buffer, Zone xml_int16, gml_surfaceProperty xml_geometry, gml_multiSurfaceProperty xml_geometry
    -> PointOnAreaOverlayer_2 [input 2]
_100m (reader GML_1)
    attributes: gml_parent_id xml_buffer, Zone xml_int16, gml_surfaceProperty xml_geometry, gml_multiSurfaceProperty xml_geometry
    -> PointOnAreaOverlayer_2 [input 2]

Bookmark: Get Coastal Zone
PointOnAreaOverlayer_2
    OV_ATTR = _overlaps
    ATTR_CONFLICT_RES = Use Original
    POLYS_FIRST = NO
    ATTR_ACCUM_MODE = Merge Incoming
    POINT -> Tester
Tester
    TEST_CLAUSE = TEST @Value(_overlaps) = 1
    TEST_MODE = Automatic
    TEST_DESCRIPTION = ""
    BOOL_OP = OR
    PASSED -> PointOnRasterValueExtractor [input 2]

Bookmark: Get Elevation
Note: CDED: DEM-Clipped [CDED]
CDED (reader CDED_1)
    -> Reprojector
Reprojector
    INTERPOLATION_TYPE_NAME = Nearest Neighbor
    SOURCE = Read from feature
    DEST = UTM83-10
    RASTER_CELL_SIZE = Preserve Cells
    REPROJECTED -> PointOnRasterValueExtractor [input 1]
PointOnRasterValueExtractor
    INTERPOLATION_TYPE_NAME = Nearest Neighbor
    POINT -> AttributeRenamer_2
AttributeRenamer_2
    ATTR_LIST = cded_accuracy_code_for_elevations,,,cded_data_edition,,,cded_file_name,,,cded_origin_code,,,cded_percent_void,,,cded_process_code,,,cded_producer,,,cded_spatial_resolution_z,,,cded_suspect_and_void_area_flag,,,cded_units,,,_band{0}.value,Elevation,
