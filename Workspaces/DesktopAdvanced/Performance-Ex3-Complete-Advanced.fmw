FME workspace Performance-Ex3-Complete-Advanced.fmw

Parameters:
- SourceDataset_OGCKML = C:\FMEData2016\Data\Boundaries\VancouverNeighborhoods.kml   # Source Google KML File or URL
- DestDataset_ESRISHAPE = C:\FMEData2016\Output   # Destination Esri Shapefile Folder
- DestDataset_ESRISHAPE_3 = C:\FMEData2016\Output   # Destination Esri Shapefile Folder
- SourceDataset_POINTCLOUDXYZ = C:\FMEData2016\Data\CellSignals\CellSignal.csv   # Point Cloud XYZ File(s)

Readers:
- OGCKML_1: OGCKML from $(SourceDataset_OGCKML)
- POINTCLOUDXYZ_1: POINTCLOUDXYZ from $(SourceDataset_POINTCLOUDXYZ)

Writers:
- ESRISHAPE_2: ESRISHAPE to $(DestDataset_ESRISHAPE_3)
- ESRISHAPE_1: ESRISHAPE to $(DestDataset_ESRISHAPE)

Neighborhoods (reader OGCKML_1)
    attributes: NeighborhoodId kml_buffer, NeighborhoodName kml_buffer, NeighborhoodURL kml_buffer, TotalPopulation2001 kml_buffer, TotalPopulation2011 kml_buffer
    -> AttributeManager
AttributeManager
    ATTR_TABLE:
      REMOVE NeighborhoodId
      REMOVE NeighborhoodURL
      REMOVE TotalPopulation2001
      REMOVE TotalPopulation2011
    -> Clipper [input 1]
POINTCLOUDXYZ (reader POINTCLOUDXYZ_1)
    -> Cloner
Cloner
    COPIES = 10
    COPYATT = _copynum
    COPY -> PointCloudFilter
PointCloudFilter
    OUTPUT_UNFILTERED_POINTS = Yes
    FILTER_TABLE = EXPRESSION_LIST @Component(Power)<-125 FILTER_ATTRIBUTE __pc_internal_filter_attribute__ FILTER_ATTRIBUTE_VALUES_LIST BadSignal
    BadSignal -> PointCloudCoercer
    <UNFILTERED> -> PointCloudCoercer_2
PointCloudCoercer
    CONVERT_TO_DISPLAY = Individual Points
    PART_NUMBER_ATTR_NAME = _part_number
    POINT_COMPONENTS = StationID Power Quality
    POINT_COMPONENTS_PRESERVE_DISPLAY = Attributes
    ACCUM_ATTRS_NAME = Yes
    COERCED -> Clipper [input 2]
Clipper
    BOUNDARY_CASES = Treat as Inside
    CREATE_AGGREGATES = Yes
    CONNECT_Z_MODE = First Wins
    ATTR_ACCUM_MODE = Merge Clipper
    CLIP_TYPE = Clippers First
    ATTR_CONFLICT_RES = Use Clippee
    CLIPPED_ATTR = _clipped
    PRESERVE_CLIPPEE_EXTENTS = Yes
    LINES_AS_SEGMENTS = No
    INSIDE -> ColdSpots (writer ESRISHAPE_1)
ColdSpots (writer ESRISHAPE_1)
    attributes: StationID number(6,0), Power number(18,13), Quality number(18,14), Neighbrhd char(254)
PointCloudCoercer_2
    CONVERT_TO_DISPLAY = Individual Points
    PART_NUMBER_ATTR_NAME = _part_number
    POINT_COMPONENTS_PRESERVE_DISPLAY = Attributes
    ACCUM_ATTRS_NAME = Yes
    COERCED -> GoodLocations (writer ESRISHAPE_2)
GoodLocations (writer ESRISHAPE_2)
