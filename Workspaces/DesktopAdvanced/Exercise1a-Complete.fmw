FME workspace Exercise1a-Complete.fmw

Parameters:
- UserNameParam = Mark Ireland   # Enter Your Name
- UserEmailParam = mark.ireland@safe.com   # Enter Your Email Address
- UserCompanyParam = Safe Software   # Enter Your Company Name

Readers:
- MITAB_1: MITAB from C:\FMEData2015\Data\Parks\Parks.tab

Writers:
- OGCKML_1: OGCKML to C:\FMEData2015\Output\Training\Parks.kml
- XML_1: XML to C:\FMEData2015\Output\Training\ParksMetadata.xml

Parks (reader MITAB_1)
    attributes: ParkId smallint, RefParkId smallint, ParkName char(40), NeighborhoodName char(40), EWStreet char(30), NSStreet char(30), DogPark char(1), Washrooms char(1), SpecialFeatures char(1)
    -> Parks (writer OGCKML_1)
    -> Sampler
Parks (writer OGCKML_1)
    attributes: ParkId kml_int16, RefParkId kml_int16, ParkName kml_char(40), NeighborhoodName kml_char(40), EWStreet kml_char(30), NSStreet kml_char(30), DogPark kml_char(1), Washrooms kml_char(1), SpecialFeatures kml_char(1)
Sampler
    SAMPLE_TYPE_LONG = First N Features
    RATE = 1
    SAMPLED -> AttributeCreator
AttributeCreator
    ATTR_LIST = AuthorName,$(UserNameParam),UpdateDate,TODAY
    -> DateFormatter
DateFormatter
    DATE_ATTR = UpdateDate
    SRCFMT = Unknown - Automatic Detection
    INVALID_DATE_VALUE = _FME_NO_OP_
    FMT = ISO DateTime (%Y-%m-%dT%H:%M:%S)
    -> ParameterFetcher
ParameterFetcher
    ATTR_LIST = AuthorEmail {$(UserEmailParam)}
    -> ParksMetadata (writer XML_1)
ParksMetadata (writer XML_1)
    attributes: AuthorName xml_char(30), AuthorEmail xml_char(30), AuthorCompany xml_char(30), UpdateDate xml_datetime
