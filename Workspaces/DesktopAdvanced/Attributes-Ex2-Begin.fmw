FME workspace Attributes-Ex2-Begin.fmw

Parameters:
- SourceDataset_CDED_3 = C:\FMEData2019\Data\ElevationModel\DEM-Clipped.dem   # Source Canadian Digital Elevation Data (CDED) File(s)
- SourceDataset_FILEGDB = C:\FMEData2019\Data\Addresses\Addresses.gdb   # File Geodatabase
- SourceDataset_GML_3 = C:\FMEData2019\Data\Boundaries\CoastalZones\CoastalZones.gml   # Source Geography Markup Language (GML) File(s)

Readers:
- CDED_2: CDED from $(SourceDataset_CDED_3)
- FILEGDB_2: FILEGDB from $(SourceDataset_FILEGDB)
- GML_2: GML from $(SourceDataset_GML_3)

Note: PostalAddress: Addresses [FILEGDB]
PostalAddress (reader FILEGDB_2)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> PointOnAreaOverlayer [POINT]
Note: CoastalZones [GML]
_100m (reader GML_2)
    attributes: Zone xml_int16, gml_surfaceProperty xml_geometry, gml_multiSurfaceProperty xml_geometry
    -> PointOnAreaOverlayer [AREA]
_200m (reader GML_2)
    attributes: Zone xml_int16, gml_surfaceProperty xml_geometry, gml_multiSurfaceProperty xml_geometry
    -> PointOnAreaOverlayer [AREA]
_300m (reader GML_2)
    attributes: Zone xml_int16, gml_surfaceProperty xml_geometry, gml_multiSurfaceProperty xml_geometry
    -> PointOnAreaOverlayer [AREA]

Bookmark: Get Coastal Zone
PointOnAreaOverlayer
    ATTR_ACCUM_MODE = Merge Incoming
    ATTR_CONFLICT_RES = Use Original
    DEAGGREGATE_INPUT = Yes
    OV_ATTR = _overlaps
    POLYS_FIRST = NO
    POINT -> Tester
Tester
    BOOL_OP = OR
    TEST_CLAUSE = TEST @Value(_overlaps) = 1
    TEST_MODE = TEST
    PASSED -> PointOnRasterValueExtractor [POINT]

Bookmark: Get Elevation
Note: CDED: DEM-Clipped [CDED]
CDED (reader CDED_2)
    -> Reprojector
Reprojector
    DEST = UTM83-10
    INTERPOLATION_TYPE_NAME = Nearest Neighbor
    RASTER_CELL_SIZE = Preserve Cells
    RASTER_TOLERANCE = 0.0
    SOURCE = Read from feature
    REPROJECTED -> PointOnRasterValueExtractor [RASTER]
PointOnRasterValueExtractor
    INTERPOLATION_TYPE_NAME = Nearest Neighbor
    POINT -> AttributeRenamer
AttributeRenamer
    ATTR_TABLE = RENAME_SET_DEFAULT _band{0}.value > Elevation
