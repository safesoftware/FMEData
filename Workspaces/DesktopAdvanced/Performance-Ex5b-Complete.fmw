FME workspace Performance-Ex5b-Complete.fmw

Parameters:
- DestDataset_GEOTIFF_3 = C:\FMEData2017\Output\Training   # Destination GeoTIFF Folder
- SourceDataset_ESRISHAPE = ""C:\FMEData2017\Data\ElevationModel\Contours\J10.shp" "C:\FMEData2017\Data\ElevationModel\Contours\J11.shp" "C:\FMEData2017\Data\ElevationModel\Contours\J12.shp" "C:\FMEData2017\Data\ElevationModel\Contours\J13.shp" "C:\FMEData2017\Data\ElevationModel\Contours\K2.shp" "C:\FMEData2017\Data\ElevationModel\Contours\K3.shp" "C:\FMEData2017\Data\ElevationModel\Contours\K4.shp" "C:\FMEData2017\Data\ElevationModel\Contours\K5.shp" "C:\FMEData2017\Data\ElevationModel\Contours\K10.shp" "C:\FMEData2017\Data\ElevationModel\Contours\K11.shp" "C:\FMEData2017\Data\ElevationModel\Contours\K12.shp" "C:\FMEData2017\Data\ElevationModel\Contours\K13.shp" "C:\FMEData2017\Data\ElevationModel\Contours\L1.shp" "C:\FMEData2017\Data\ElevationModel\Contours\L2.shp" "C:\FMEData2017\Data\ElevationModel\Contours\L3.shp" "C:\FMEData2017\Data\ElevationModel\Contours\L4.shp" "C:\FMEData2017\Data\ElevationModel\Contours\L5.shp" "C:\FMEData2017\Data\ElevationModel\Contours\L6.shp" "C:\FMEData2017\Data\ElevationModel\Contours\L7.shp" "C:\FMEData2017\Data\ElevationModel\Contours\L9.shp" "C:\FMEData2017\Data\ElevationModel\Contours\L10.shp" "C:\FMEData2017\Data\ElevationModel\Contours\L11.shp" "C:\FMEData2017\Data\ElevationModel\Contours\L12.shp" "C:\FMEData2017\Data\ElevationModel\Contours\L13.shp" "C:\FMEData2017\Data\ElevationModel\Contours\M1.shp" "C:\FMEData2017\Data\ElevationModel\Contours\M2.shp" "C:\FMEData2017\Data\ElevationModel\Contours\M3.shp" "C:\FMEData2017\Data\ElevationModel\Contours\M4.shp" "C:\FMEData2017\Data\ElevationModel\Contours\M5.shp" "C:\FMEData2017\Data\ElevationModel\Contours\M6.shp" "C:\FMEData2017\Data\ElevationModel\Contours\M7.shp" "C:\FMEData2017\Data\ElevationModel\Contours\M8.shp" "C:\FMEData2017\Data\ElevationModel\Contours\M9.shp" "C:\FMEData2017\Data\ElevationModel\Contours\M10.shp" "C:\FMEData2017\Data\ElevationModel\Contours\M11.shp" "C:\FMEData2017\Data\ElevationModel\Contours\M12.shp" "C:\FMEData2017\Data\ElevationModel\Contours\M13.shp" "C:\FMEData2017\Data\ElevationModel\Contours\N3.shp" "C:\FMEData2017\Data\ElevationModel\Contours\N4.shp" "C:\FMEData2017\Data\ElevationModel\Contours\N5.shp" "C:\FMEData2017\Data\ElevationModel\Contours\N6.shp" "C:\FMEData2017\Data\ElevationModel\Contours\N7.shp" "C:\FMEData2017\Data\ElevationModel\Contours\N8.shp" "C:\FMEData2017\Data\ElevationModel\Contours\N9.shp" "C:\FMEData2017\Data\ElevationModel\Contours\N10.shp" "C:\FMEData2017\Data\ElevationModel\Contours\N11.shp" "C:\FMEData2017\Data\ElevationModel\Contours\N12.shp" "C:\FMEData2017\Data\ElevationModel\Contours\N13.shp" "C:\FMEData2017\Data\ElevationModel\Contours\O4.shp" "C:\FMEData2017\Data\ElevationModel\Contours\O5.shp" "C:\FMEData2017\Data\ElevationModel\Contours\O6.shp" "C:\FMEData2017\Data\ElevationModel\Contours\O7.shp" "C:\FMEData2017\Data\ElevationModel\Contours\O8.shp" "C:\FMEData2017\Data\ElevationModel\Contours\O9.shp" "C:\FMEData2017\Data\ElevationModel\Contours\O10.shp" "C:\FMEData2017\Data\ElevationModel\Contours\O11.shp" "C:\FMEData2017\Data\ElevationModel\Contours\O12.shp" "C:\FMEData2017\Data\ElevationModel\Contours\O13.shp" "C:\FMEData2017\Data\ElevationModel\Contours\P7.shp" "C:\FMEData2017\Data\ElevationModel\Contours\P8.shp" "C:\FMEData2017\Data\ElevationModel\Contours\P9.shp" "C:\FMEData2017\Data\ElevationModel\Contours\P10.shp" "C:\FMEData2017\Data\ElevationModel\Contours\P11.shp" "C:\FMEData2017\Data\ElevationModel\Contours\P12.shp" "C:\FMEData2017\Data\ElevationModel\Contours\P13.shp" "C:\FMEData2017\Data\ElevationModel\Contours\Q6.shp" "C:\FMEData2017\Data\ElevationModel\Contours\Q7.shp" "C:\FMEData2017\Data\ElevationModel\Contours\Q8.shp" "C:\FMEData2017\Data\ElevationModel\Contours\Q9.shp" "C:\FMEData2017\Data\ElevationModel\Contours\Q10.shp" "C:\FMEData2017\Data\ElevationModel\Contours\Q11.shp" "C:\FMEData2017\Data\ElevationModel\Contours\Q12.shp" "C:\FMEData2017\Data\ElevationModel\Contours\Q13.shp" "C:\FMEData2017\Data\ElevationModel\Contours\R7.shp" "C:\FMEData2017\Data\ElevationModel\Contours\R8.shp" "C:\FMEData2017\Data\ElevationModel\Contours\R9.shp" "C:\FMEData2017\Data\ElevationModel\Contours\R10.shp" "C:\FMEData2017\Data\ElevationModel\Contours\R11.shp" "C:\FMEData2017\Data\ElevationModel\Contours\R12.shp" "C:\FMEData2017\Data\ElevationModel\Contours\R13.shp""   # Source Esri Shapefile(s)
- FEATURE_TYPES =

Readers:
- ESRISHAPE_1: ESRISHAPE from $(SourceDataset_ESRISHAPE)

Writers:
- GEOTIFF_2: GEOTIFF to $(DestDataset_GEOTIFF_3)

J10 (reader ESRISHAPE_1)
    attributes: Elevation char(30), Grid char(30)
    -> 3DForcer
Note: No parallel processing options exist for the 3DForcer transformer
3DForcer
    ZVALATTR = @Value(Elevation)
    KEEPZVAL = No
    -> RasterDEMGenerator [POINTS/LINES]
Note: Turn vector contour tiles / into raster DEM tiles
Note: A parallel processing option exists for the RasterDEMGenerator transformer / fme_feature_type (the original file name) is already used to group by, / and so parallel processing can be simply turned on immediately / DEM generation is a slow process, so this is a good candidate for parallel processing. Try using different degrees of parallelization for the best balance.
RasterDEMGenerator
    TOLERANCE = 1
    Y_SPACING = 0.5
    GROUP_BY = fme_feature_type
    INTERPOLATION_TYPE = AUTO
    X_SPACING = 0.5
    NODATA_VALUE = -32767.0
    DEM_RASTER -> RasterDEM (writer GEOTIFF_2)
RasterDEM (writer GEOTIFF_2)
