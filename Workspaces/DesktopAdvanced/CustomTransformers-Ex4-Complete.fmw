FME workspace CustomTransformers-Ex4-Complete.fmw

Parameters:
- SourceDataset_ESRISHAPE = C:\FMEData2019\Data\Transportation\Cycling\BikePaths_M.shp   # Source Esri Shapefile(s)

Readers:
- ESRISHAPE_2: ESRISHAPE from $(SourceDataset_ESRISHAPE)

BikePaths_M (reader ESRISHAPE_2)
    attributes: PathId long, PathName char(30), PathLength long, PathType char(1)
    -> Snapper
Snapper
    EXTEND_LINES = NEVER
    SAVE_SHORT_LINES = No
    SNAPTYPE_PARAM = End Point Snapping
    TOLERANCE = 3
    SNAPPED -> LineCombiner
    UNTOUCHED -> LineCombiner
LineCombiner
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = Yes
    LINES_AS_SEGMENTS = No
    PRESERVE = no
    TOPOLOGY = End noded
    LINE -> AverageLengthCalculator [Lines]
AverageLengthCalculator
