FME workspace Exercise3a-Begin.fmw

Parameters:
- SourceDataset_OGCKML = C:\FMEData2015\Data\Boundaries\VancouverNeighborhoods.kml   # Source Google Earth KML File or URL

Readers:
- OGCKML_1: OGCKML from $(SourceDataset_OGCKML)

Neighborhoods (reader OGCKML_1)
    attributes: NeighborhoodId kml_buffer, NeighborhoodName kml_buffer, NeighborhoodURL kml_buffer, TotalPopulation2001 kml_buffer, TotalPopulation2011 kml_buffer
    -> CsmapReprojector
CsmapReprojector
    VERTICAL_HANDLING = Ignore heights and leave them unchanged
    DEST = UTM83-10
    RASTER_CELL_SIZE = Preserve Cells
    INTERPOLATION_TYPE_NAME = Nearest Neighbor
    REPROJECTED -> AreaCalculator
Note: Calculate Area in SQ KM
AreaCalculator
    AREA_ATTR = NeighborhoodArea
    MULT = .000001
    AREA_TYPE = Plane Area
    -> ExpressionEvaluator_3
ExpressionEvaluator_3
    EXPRESSION = @Value(TotalPopulation2001)/@Value(NeighborhoodArea)
    ACTION = Create New Attribute
    VAL_ATTR = PopulationDensity2001
    -> ExpressionEvaluator_4
ExpressionEvaluator_4
    EXPRESSION = @Value(TotalPopulation2011)/@Value(NeighborhoodArea)
    ACTION = Create New Attribute
    VAL_ATTR = PopulationDensity2011
    -> ExpressionEvaluator_2_Output
ExpressionEvaluator_2_Output: Inspector
